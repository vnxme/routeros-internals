-- *****************************************************************
-- COLUBRIS-TC.my:  Colubris Networks MIB Textual Conventions
--
-- November 2001
--
-- Copyright (c) 2001, 2002 by Colubris Networks, Inc.
-- All rights reserved.
-- 
-- *****************************************************************
--

COLUBRIS-TC DEFINITIONS ::= BEGIN

IMPORTS
    MODULE-IDENTITY,
    Gauge32,
    Integer32
        FROM SNMPv2-SMI
    TEXTUAL-CONVENTION
        FROM SNMPv2-TC
    colubrisModules
        FROM COLUBRIS-SMI;


colubrisTextualConventions MODULE-IDENTITY
	LAST-UPDATED "200111090000Z"
	ORGANIZATION "Colubris Networks, Inc."
	CONTACT-INFO
		"	Colubris Networks

		Postal: 420 Armand-Frappier, Suite 200
			Laval, QC  H7V 4B4
			CANADA

		   Tel: +1 450 680-1661

		E-mail: cn-snmp@colubris.com"
    DESCRIPTION
        "This module defines textual conventions used in the
        Colubris Networks enterprise MIBs."
    ::= { colubrisModules 1 }

END
