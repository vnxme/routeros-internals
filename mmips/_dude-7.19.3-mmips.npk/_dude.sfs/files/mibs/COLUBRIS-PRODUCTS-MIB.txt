-- *****************************************************************
-- COLUBRIS-PRODUCTS-MIB.my:  Colubris Product Object Identifier Assignments
--
--
-- November 2001
--
-- Copyright (c) 2000, 2001, 2002  by Colubris Networks, Inc.
-- All rights reserved.
-- 
-- *****************************************************************


COLUBRIS-PRODUCTS-MIB DEFINITIONS ::= BEGIN

IMPORTS
	MODULE-IDENTITY
		FROM SNMPv2-SMI
	colubrisProducts,
	colubrisModules
		FROM COLUBRIS-SMI;

colubrisProductsMIB MODULE-IDENTITY
	LAST-UPDATED	"200111090000Z"
	ORGANIZATION	"Colubris Networks, Inc."
	CONTACT-INFO
		"	Colubris Networks

		Postal: 420 Armand-Frappier, Suite 200
			Laval, QC  H7V 4B4
			CANADA

		   Tel: +1 450 680-1661

		E-mail: cn-snmp@colubris.com"
  	DESCRIPTION
		"Initial version."
	::= { colubrisModules 2 }

colubrisCN100 OBJECT IDENTIFIER ::= { colubrisProducts 0 }
colubrisCN1000 OBJECT IDENTIFIER ::= { colubrisProducts 1 }
colubrisCN1000HEREUARE OBJECT IDENTIFIER ::= { colubrisProducts 2 }
colubrisCN1050 OBJECT IDENTIFIER ::= { colubrisProducts 3 }
colubrisCN1054 OBJECT IDENTIFIER ::= { colubrisProducts 4 }
colubrisCN3000 OBJECT IDENTIFIER ::= { colubrisProducts 5 }
colubrisCN100HEREUARE OBJECT IDENTIFIER ::= { colubrisProducts 6 }
colubrisCN100TRAVELNET OBJECT IDENTIFIER ::= { colubrisProducts 7 }
colubrisCN300 OBJECT IDENTIFIER ::= { colubrisProducts 8 }
colubrisCN1150 OBJECT IDENTIFIER ::= { colubrisProducts 9 } 
colubrisCN3100 OBJECT IDENTIFIER ::= { colubrisProducts 10 }
colubrisCN1000LIGHT OBJECT IDENTIFIER ::= { colubrisProducts 11 }
colubrisCN3500 OBJECT IDENTIFIER ::= { colubrisProducts 12 }
colubrisCN310 OBJECT IDENTIFIER ::= { colubrisProducts 13 }

END
