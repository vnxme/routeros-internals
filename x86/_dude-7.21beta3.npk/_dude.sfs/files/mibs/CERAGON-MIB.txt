CERAGON-MIB DEFINITIONS ::= BEGIN
--Title:     CERAGON   MIB

-- Copyright 1997 CERAGON.
-- All Rights Reserved.

-- It is CERAGON's intent to encourage the widespread use of
-- this Specification in connection with the management of
-- CERAGON's products. CERAGON grants vendors, end-users,
-- and other interested parties a non-exclusive license to
-- use this Specification in connection with the management
-- of CERAGON's products.

-- This Specification is supplied "as is," and CERAGON makes
-- no warranty, either express or implied, as to the use,
-- operation, condition, or performance of the Specification.

IMPORTS
      Counter, enterprises,
       IpAddress, Gauge       FROM RFC1155-SMI
      DisplayString, ifIndex          FROM RFC1213-MIB
      OBJECT-TYPE                     FROM RFC-1212
      TRAP-TYPE                       FROM RFC-1215;
--      Gauge32                    FROM SNMPv2-SMI;
--      sonetSectionCurrentStatus  FROM SONET-MIB;
--      RowStatus                       FROM SNMPv2-TC;



-- Some MIB compilers need those two lines:
-- enterprises OBJECT IDENTIFIER ::=
--		     { iso org(3) dod(6) internet(1) private(4) 1 }


ceragon OBJECT IDENTIFIER ::= { enterprises 2281 }

--Version:   3.28c	   (supported by IDC version I522)
--First Version Date:   15.04.97

--Last Update: 17.08.2004


gnOID OBJECT IDENTIFIER ::= { ceragon 1}  --    list of CERAGON products

gnFirstOID OBJECT IDENTIFIER ::= { gnOID 1 } -- First product

gnSystem OBJECT IDENTIFIER ::= { ceragon 2 }

--This group contains general parameters of the system.
gnGeneral OBJECT IDENTIFIER ::= { gnSystem 1}

--gnGenHWVersion OBJECT-TYPE
--	SYNTAX  DisplayString
--	ACCESS  read-only
--	STATUS mandatory
--	DESCRIPTION
--	"This parameter specifies the version of the hardware."
--	::= { gnGeneral 1 }

--gnGenSWVersion OBJECT-TYPE
--	SYNTAX  DisplayString
--	ACCESS  read-only
--	STATUS mandatory
--	DESCRIPTION
--	"This parameter specifies the version of the software."
--	::= { gnGeneral 2 }

gnGenStandardOrg OBJECT-TYPE
	SYNTAX  INTEGER {
		etsi(2),
		fcc(3),
		japan(4),
		lmds(5),
		cmds(6),
		australia(7),
		other(8)
	}
	ACCESS  read-only
	STATUS mandatory
	DESCRIPTION
	"This parameter specifies which international standard is used."
	::= { gnGeneral 1 }

gnGenTxFreqRange OBJECT-TYPE
	SYNTAX  INTEGER {
		from37000to37350(2), -- FCC RX Range: 37700->38050
		from37350to37700(3), -- FCC RX Range: 38050->38400
		from37700to38050(4), -- FCC
		from38050to38400(5), -- FCC
		from38600to38950(6), -- FCC RX Range: 39300->39650
		from38950to39300(7),  -- FCC RX Range: 39650->40000
                from39300to39650(8), -- FCC
		from39650to40000(9),  --FCC
                from37058to37618(10), --ETSI  RX Range: 38318->38878
                from37618to38178(11), --ETSI  RX Range: 38878->39438
                from38318to38878(12), --ETSI
                from38878to39438(13), --ETSI
                notUsed(14)

		}
	ACCESS  read-only
	STATUS mandatory
	DESCRIPTION
	"This parameter specifies frequency ranges in Hertz. Value 1 to 13 are used 
when the link
	 is working with channels. The notUsed value is used when the link is 
working with frequency."
	::= { gnGeneral 2 }

gnGenRemoteConnection OBJECT-TYPE
	SYNTAX  INTEGER {
		connected(2),
		disconnected(3)
	}
	ACCESS  read-only
	STATUS mandatory
	DESCRIPTION
	"Is the connection between the local manager and
	 the remote manager."
	::= { gnGeneral 3 }

gnGenRemoteDistance OBJECT-TYPE
	SYNTAX  INTEGER (100..30000)
	ACCESS  read-write
	STATUS mandatory
	DESCRIPTION
	"This field is the distance between the local and remote ODU, in meters.
	This attribute does not auto-detect the distance.
	It is used as part of the unfaded RSL calculation feature in CERAGONView."
	::= { gnGeneral 4 }

gnGenInterLenLocalRemote OBJECT-TYPE
	SYNTAX  INTEGER
	ACCESS  read-write
	STATUS mandatory
	DESCRIPTION
	"This field is the FEC interleaver length - DONT CHANGE THIS FIELD !!!.
	WRITE will change both local and remote sides."
	::= { gnGeneral 5 }

gnGenTxFreqLocalRemote OBJECT-TYPE
	SYNTAX  INTEGER (0..20)
	ACCESS  read-write
	STATUS mandatory
	DESCRIPTION
	"This parameter indicates the radio TX channel number.
	WRITE will change both LOCAL and REMOTE sides.
	Not all radios will support TX frequency change via channel numbers."
	DEFVAL { 1}
	::= { gnGeneral 6}


gnGenRealTimeandDate OBJECT-TYPE
	SYNTAX OCTET STRING(SIZE(8))
	ACCESS  read-write
	STATUS mandatory
	DESCRIPTION
	"This parameter specifies the real time and date
          Format 'YYYY-MM-DD,HH:MM:SS' (Hexadecimal).
            A date-time specification.

            field  octets  contents                  range
            -----  ------  --------                  -----
              1      1-2   year                      0..65536
              2       3    month                     1..12
              3       4    day                       1..31
              4       5    hour                      0..23
              5       6    minutes                   0..59
    	      6       7    seconds                   0..60
                           (use 60 for leap-second)
              7       8    deci-seconds              0..9
              8       9    direction from UTC        '+' / '-'
              9      10    hours from UTC            0..11
             10      11    minutes from UTC          0..59

            For example, Tuesday May 26, 1992 at 1:30:15 PM EDT
            would be displayed as:	07 c8 05 1a 0d 1e 0f 00
								  ( 1992 -5 -26,13:30:15 )

            Note that if only local time is known, then timezone
            information (fields 8-10) is not present."

	::= { gnGeneral 7 }


gnGenCfgDeviceTable  OBJECT-TYPE
        SYNTAX  SEQUENCE OF GnGenCfgDeviceEntry
        ACCESS  not-accessible
        STATUS mandatory
        DESCRIPTION
        "This table contains general configuration info
          per device, local and remote."
        ::= { gnGeneral 8 }


gnGenCfgDeviceEntry OBJECT-TYPE
        SYNTAX GnGenCfgDeviceEntry
        ACCESS  not-accessible
        STATUS mandatory
	  DESCRIPTION
	  "Entry containing general configuration information, for both local and 
remote sides."
        INDEX { gnGenCfgDeviceId }
        ::= { gnGenCfgDeviceTable 1 }

GnGenCfgDeviceEntry ::=
            SEQUENCE {
	gnGenCfgDeviceId
          	   INTEGER,
	gnGenCfgDeviceResetPerfMon
	  INTEGER,
	gnGenCfgDeviceOperation
	  INTEGER,
	gnGenCfgActivateLoopback
	  INTEGER,
	gnGenCfgF1DataChanConnector -- was LineConnector; 
-- if DB9 connector, indicates NEW regenerator hardware.
	  INTEGER,
	gnGenCfgWaySideConnector --was RadioConnector
                INTEGER,
        gnGenCfgActivateChanLoopback
                  INTEGER,
        gnGenCfgInterLenLocalOnly
                 INTEGER ,
	gnGenCfgSlipIp
	         IpAddress,
	gnGenCfgSlipModemConnection
	         DisplayString,
	gnGenCfgSlipSpeed
	         INTEGER,
	gnGenCfgAlarmSeverity
	        OCTET STRING,
	gnGenCfgODUSerialNumber
	        DisplayString,
	gnGenCfgIDUSerialNumber
	        DisplayString,
	gnGenCfgAlarmText
	        DisplayString,
	gnGenCfgTrapSeverity
	         INTEGER,
	gnGenCfgProductType		  -- merge with tftp
			INTEGER,
	gnGenCfgLeftMediumConnector
            INTEGER,
	gnGenCfgMiddleMediumConnector
            INTEGER,
    gnGenCfgPrimaryClockSource
			INTEGER,
    gnGenCfgSecondaryClockSource
			INTEGER,
	gnGenCfgTrapOption
	         INTEGER,
	gnGenCfgCLLI
			DisplayString,
	gnGenCfgHeartbeatPeriod
	         INTEGER,
	gnGenCfgGetRemoteData
			INTEGER,
	gnGenCfgClearLoopTimeout
			INTEGER,
	gnGenCfgSubProductType
			INTEGER
	}

gnGenCfgDeviceId OBJECT-TYPE
	SYNTAX  INTEGER {
		local(1),
		remote(2)
	}
        	ACCESS  read-only
   	STATUS mandatory
        	DESCRIPTION
              "This value indicates the device table entry (local or 
Remote)."
        ::= { gnGenCfgDeviceEntry 1 }


gnGenCfgDeviceResetPerfMon OBJECT-TYPE
	SYNTAX  INTEGER {
		reset(2),
		noAction(3),
		clearFastEthernetStatistics(4)
	}
	ACCESS  read-write
	STATUS mandatory
	DESCRIPTION
	"Reset performance monitoring. "
	DEFVAL { noAction }
	::= { gnGenCfgDeviceEntry 2 }

gnGenCfgDeviceOperation OBJECT-TYPE
	SYNTAX  INTEGER {
		noOperation(2),
        softwareReset(3),
        setDefaultConf(4),
		clearMainManagerSoftware(5),
		resetODU(6),
		resetMUX(7),
		resetSwOdu(8)
	}
	ACCESS  read-write
	STATUS mandatory
	DESCRIPTION
	"This parameter allows the NMS to perform operations.
      (3) will implement software RESET
      (4) will SET all factory default configurations, including IP address!
      (5) will CLEAR IDU software
	NOTE: CLEARING IDU software will cause the IDU to use the factory BOOT 
software version.
	  4 and 5 will take place only after reset of the IDU"
	DEFVAL { noOperation }
	::= { gnGenCfgDeviceEntry 3 }


gnGenCfgActivateLoopback OBJECT-TYPE
	SYNTAX  INTEGER {
		noOperation(2),
                loopbackSPI(3),
---            	loopbackMUX(4),
              	loopbackMDM(5),
		loopbackOuterSPI(6),
--		localTechnSPIloopback(7),
--             	localTechnMUXloopback(8),
--             	localTechnMDMloopback(9),
                localODUloopback(10)
	}
	ACCESS  read-write
	STATUS mandatory
	DESCRIPTION
	"This parameter controls the loop back diagnostics operations.
	For remote units, only SPI, MUX and MDM loopbacks are allowed.
	"
	DEFVAL { noOperation }
	::= { gnGenCfgDeviceEntry 4 }

gnGenCfgF1DataChanConnector OBJECT-TYPE
	SYNTAX  INTEGER {
		noInterface(1), -- No interface
		rs232db25(2),  -- V24
		v35(3),
                rs422db25(4),  --RS-530
                rj45CoDirect(5),
		rj45bridge(6), -- Ethernet bridge
                x21db15(7),
		rs232db9(8)    -- New regenerator hardware
	}
	ACCESS  read-only
	STATUS mandatory
	DESCRIPTION
	"This is the physical interface of the F1 line data channel
	(USER CHANNEL connection). "
	DEFVAL { rs232db25 }
	::= { gnGenCfgDeviceEntry 5 }

gnGenCfgWaySideConnector OBJECT-TYPE
	SYNTAX  INTEGER {
		noInterface(1), -- No interface
		rs232db25(2),  -- V24
		v35(3),
                rs422db25(4),  -- RS-530
                connectorE1(5),
		rj45bridge(6), -- Ethernet Bridge
                x21db15(7),
                connectorT1(8),
				lineSTM4(9),	
        clockUnit2M(10),
        clockUnit1dot5M(11)	
	}
	ACCESS  read-only
	STATUS mandatory
	DESCRIPTION
	"This is the physical interface of the radio E1 way side channel
	(WAYSIDE CHANNEL connection)."
	DEFVAL { rs232db25 }
	::= { gnGenCfgDeviceEntry 6 }


gnGenCfgActivateChanLoopback OBJECT-TYPE
	SYNTAX  INTEGER {
		noOperation(2),
              	loopbackDataChan(3),
              	loopbackWaySide(4)

	}
	ACCESS  read-write
	STATUS mandatory
	DESCRIPTION
	"This parameter controls the USER CHANNEL and WAYSIDE channel
	loopback diagnostic operations.
	(3) will activate the 64k data channel loopback (USER CHANNEL)
      (4) will activate the WAYSIDE CHANNEL loopback."
	DEFVAL { noOperation }
	::= { gnGenCfgDeviceEntry 7 }


gnGenCfgInterLenLocalOnly OBJECT-TYPE
	SYNTAX  INTEGER
	ACCESS  read-write
	STATUS mandatory
	DESCRIPTION
	"This field is the FEC interleaver length .DONT CAHNGE THIS FIELD !!! .
	WRITE will change the local side only."
	::= { gnGenCfgDeviceEntry 8 }


gnGenCfgSlipIp OBJECT-TYPE
	SYNTAX  IpAddress
	ACCESS  read-write
	STATUS mandatory
	DESCRIPTION
	"This is the SERIAL interface IP address.
	Included for future development, not currently supported."
	::= { gnGenCfgDeviceEntry 9 }

gnGenCfgSlipModemConnection OBJECT-TYPE
	SYNTAX  DisplayString
	ACCESS  read-write
	STATUS mandatory
	DESCRIPTION
	"The telephone number to which the modem will initialize a call,
	upon generation of a TRAP.
	The number must be entered numerically (for example 18001234567)."
	::= { gnGenCfgDeviceEntry 10 }


gnGenCfgSlipSpeed OBJECT-TYPE
	SYNTAX  INTEGER {
		baud9600(1),
		baud19200(2),
		baud38400(3),
		baud57600(4),
		baud115200(5)
	}
              ACCESS  read-write
              STATUS  mandatory
              DESCRIPTION
              "The SERIAL interface baud rate."
              ::= { gnGenCfgDeviceEntry 11 }


gnGenCfgAlarmSeverity  OBJECT-TYPE
	      SYNTAX OCTET STRING(SIZE(15))
              ACCESS  read-write
              STATUS  mandatory
              DESCRIPTION
              "This field is used only by the Ceraview management 
application
			   Every Trap severity 4 bits.
		 15 (MAJOR), 7 (MINOR), 3 (WARNING) and 1 (EVENT) options.
		 The first 4 bits ODU Power supply severity,
	       then the Synthesizer severity ,then Tx level then RX level
	       ODU temperature, ODU loopback , IDU power supply , Cable,
	       Modem, IDU temperature, IDU loopbacks, External Alarm 1,
	       External Alarm 2 ,External Alarm 3, External Alarm 4,
	       External Alarm 5, External Alarm 6, External Alarm 7,
	       External Alarm 8, Remote connectivity, LOF, LOS, EXC, SD
	       J0 mismatch and system fault."
              ::= { gnGenCfgDeviceEntry 12 }

gnGenCfgODUSerialNumber OBJECT-TYPE
	SYNTAX  DisplayString
	ACCESS  read-only
	STATUS mandatory
	DESCRIPTION
	"This is the ODU serial number - up to 20 characters "
	::= { gnGenCfgDeviceEntry 13 }

gnGenCfgIDUSerialNumber OBJECT-TYPE
	SYNTAX  DisplayString
	ACCESS  read-only
	STATUS mandatory
	DESCRIPTION
	"This is the IDU serial number - up to 20 characters "
	::= { gnGenCfgDeviceEntry 14}

gnGenCfgAlarmText OBJECT-TYPE
	SYNTAX  DisplayString
	ACCESS  read-only
	STATUS mandatory
	DESCRIPTION
	"The private trap text, describing the last generated trap text."
	::= { gnGenCfgDeviceEntry 15}

gnGenCfgTrapSeverity OBJECT-TYPE

	SYNTAX  INTEGER
	{
		clear		(0),
		event		(1),
		warning		(3),
		minor		(7),
		major		(15),
		critical	(31)
	}
        ACCESS  read-only
        STATUS  mandatory
        DESCRIPTION
        "The current Trap severity, describing the last generated trap 
severity"
         ::= { gnGenCfgDeviceEntry 16 }
-- *******************************************************************
-- The following fields were added for the Access product
-- *******************************************************************

gnGenCfgProductType	OBJECT-TYPE
	SYNTAX  INTEGER
		{
				accessMux 	   			(2),
    			sdhRegenerator 			(3),
				narrowBandPdhRepeater	(4),
				accessMuxStm0			(5),
				plex6200				(6),
				adm						(7)
		}
        ACCESS  read-only
        STATUS  mandatory
        DESCRIPTION
        "The product type."
         ::= { gnGenCfgDeviceEntry 17 }


gnGenCfgLeftMediumConnector OBJECT-TYPE
	SYNTAX  INTEGER {
		noInterface(1), -- No interface
		twoDS3(2),
		oneDS3(3),
                twoE3(4),
                oneE3(5),
		oneFastEthernet(6),
		fiberSTM1(7),
		electricalSTM1(8),
		utpSTM1(9),
		stpSTM1(10),
		twoSTM1(11),
		eightE1(12),
		eightT1(13),
		hitLess(14),
		fiberSTM1Trib(15),
		electricalSTM1Trib(16),
		hitLessWithBridge(17),
		opticalFastEthernet(18)
	}
	ACCESS  read-only
	STATUS mandatory
	DESCRIPTION
	"For ACCESS hardware, this indicates the first (left) interface connector."
	DEFVAL { twoDS3 }
	::= { gnGenCfgDeviceEntry 18 }

gnGenCfgMiddleMediumConnector OBJECT-TYPE
	SYNTAX  INTEGER {
		noInterface(1), -- No interface
		twoDS3(2),
		oneDS3(3),
                twoE3(4),
                oneE3(5),
		oneFastEthernet(6),
		fiberSTM1(7),
		electricalSTM1(8),
		utpSTM1(9),
		stpSTM1(10),
		twoSTM1(11),
		eightE1(12),
		eightT1(13),
		hitLess(14),
		fiberSTM1Trib(15),
		electricalSTM1Trib(16),
		hitLessWithBridge(17),
		opticalFastEthernet(18)
	}
	ACCESS  read-only
	STATUS mandatory
	DESCRIPTION
	"For ACCESS hardware, this indicates the second (right)interface connector."
	DEFVAL { oneDS3 }
	::= { gnGenCfgDeviceEntry 19 }

gnGenCfgPrimaryClockSource OBJECT-TYPE
	SYNTAX  INTEGER {
				internalClock(2),
                external2MB(3),
                radioClock(4),
                fiberClock(5),
                external2MHz(6),
                external1AndHalfMB(7),
				tributaryClock1(8),
				tributaryClock2(9),
				tributaryClock3(10),
				tributaryClock4(11),
				tributaryClock5(12),
				tributaryClock6(13),
				tributaryClock7(14),
				tributaryClock8(15),
				tributaryClock9(16),
				tributaryClock10(17),
				tributaryClock11(18),
				tributaryClock12(19),
				tributaryClock13(20),
				tributaryClock14(21),
				tributaryClock15(22),
				tributaryClock16(23),
				tribSTM1(24)
	}
	ACCESS  read-write
	STATUS mandatory
	DESCRIPTION
	"The primary clock source, configurable for ACCESS radios only."
        DEFVAL { internalClock }
	::= { gnGenCfgDeviceEntry 20 }

gnGenCfgSecondaryClockSource OBJECT-TYPE
	SYNTAX  INTEGER {
				internalClock(2),
                external2MB(3),
                radioClock(4),
                fiberClock(5),
                external2MHz(6),
                external1AndHalfMB(7),
				tributaryClock1(8),
				tributaryClock2(9),
				tributaryClock3(10),
				tributaryClock4(11),
				tributaryClock5(12),
				tributaryClock6(13),
				tributaryClock7(14),
				tributaryClock8(15),
				tributaryClock9(16),
				tributaryClock10(17),
				tributaryClock11(18),
				tributaryClock12(19),
				tributaryClock13(20),
				tributaryClock14(21),
				tributaryClock15(22),
				tributaryClock16(23),
				tribSTM1(24)
        }
	ACCESS  read-write
	STATUS mandatory
	DESCRIPTION
	"The secondary clock source, configurable for ACCESS radios only."
        DEFVAL { internalClock }
	::= { gnGenCfgDeviceEntry 21 }

gnGenCfgTrapOption OBJECT-TYPE
	SYNTAX INTEGER (0..31)
	ACCESS read-write
	STATUS mandatory
	DESCRIPTION
	" This item defines various trap options (0-31):

	  0 - SNSN (STANDARD TRAPS DO NOT INCLUDE SERIAL NUMBER)
	  1 - ASN  (ALL TRAPS INCLUDE SERIAL NUMBER)
	  2 - SNSN, DNLR (DO NOT REPORT LOCAL TRAPS FROM REMOTE IDU)
	  3 - ASN, DNLR
	  4 - SNSN, EVT (USE DIFFERENT TRAP ID FOR EACH ALARM TYPE)
	  5 - ASN, EVT
	  6 - SNSN, DNLR, EVT
	  7 - ASN, DNLR, EVT 
	  
	  * - Add 8 to your choice for excluding traps with id >= 128.
	  	  Example: for SNSN, DNLR with this filter write 10 (=8+2).
	  ** - Add another 16 to your choice in order to send 'clear' traps with zero severity."
	DEFVAL { 0 }
	::= { gnGenCfgDeviceEntry 22 }

gnGenCfgCLLI OBJECT-TYPE
	SYNTAX DisplayString (SIZE(0..30))
	ACCESS read-write
	STATUS mandatory
	DESCRIPTION
	" Common Language Location Identifier (maximum length: 30)"
	::= { gnGenCfgDeviceEntry 23 }

gnGenCfgHeartbeatPeriod OBJECT-TYPE
	SYNTAX INTEGER (0..65535)
	ACCESS read-write
	STATUS mandatory
	DESCRIPTION
	" This item defines the number of minutes between each trap"
	DEFVAL { 0 }
	::= { gnGenCfgDeviceEntry 24 }

gnGenCfgGetRemoteData OBJECT-TYPE
	SYNTAX  INTEGER {
				off(2),
             	on(3)
				}
    ACCESS  read-write
    STATUS mandatory
	DESCRIPTION
	"."
	DEFVAL	{on}
    ::= { gnGenCfgDeviceEntry 25 }

gnGenCfgClearLoopTimeout OBJECT-TYPE
	SYNTAX INTEGER (0..1440)
	ACCESS read-write
	STATUS mandatory
	DESCRIPTION
	"  This item defines the clear loopbacks timeout in minutes.
	possible values: 0..1440. 
	0 means disable. "
	DEFVAL { 0 }
	::= { gnGenCfgDeviceEntry 26 }

gnGenCfgSubProductType OBJECT-TYPE
	SYNTAX  INTEGER
        ACCESS  read-only
        STATUS mandatory
		DESCRIPTION
		"lsb bit: 1 if fibeair 1500i or 1528i 0 otherwise."
        ::= { gnGenCfgDeviceEntry 27 }


gnGenStatDeviceTable  OBJECT-TYPE
        SYNTAX  SEQUENCE OF GnGenStatDeviceEntry
        ACCESS  not-accessible
        STATUS mandatory
        DESCRIPTION
        "This table contains general configuration info
          per device; local and remote."
        ::= { gnGeneral 9 }


gnGenStatDeviceEntry OBJECT-TYPE
        SYNTAX GnGenStatDeviceEntry
        ACCESS  not-accessible
        STATUS mandatory
	  DESCRIPTION
	  "Entry containing general configuration information per device, both 
local and remote sides."
        INDEX { gnGenStatDeviceId }
        ::= { gnGenStatDeviceTable 1 }

GnGenStatDeviceEntry ::=
            SEQUENCE {
	gnGenStatDeviceId
             INTEGER,
	gnGenStatDeviceCelsiusTemp
	     INTEGER,
	gnGenStatDeviceFahrenheitTemp
	     INTEGER,
-- The following variables are concerning the service of the IDU
	gnGenStatDevicePowerSupply
	  OCTET STRING,
	gnGenStatDeviceCable
	  INTEGER,
	gnGenStatDeviceDryContact
	  OCTET STRING,
	gnGenStatDeviceLeds
	  OCTET STRING,
	gnGenStatInternalCommunication
	   OCTET STRING ,
        gnGenStatDeviceFanStatus
	   OCTET STRING,
	gnGenStatDeviceODUStatus
	   OCTET STRING,
	gnGenStatDeviceIDUStatus
	   OCTET STRING,
	gnGenStatDeviceRSTStatus
	   OCTET STRING

}


gnGenStatDeviceId OBJECT-TYPE
	SYNTAX  INTEGER {
		local(1),
		remote(2)
	}
        ACCESS  read-only
   	STATUS mandatory
        DESCRIPTION
        "This value indicates which device is involved
	in the specific row."
        ::= { gnGenStatDeviceEntry 1 }

gnGenStatDeviceCelsiusTemp OBJECT-TYPE
        SYNTAX  INTEGER (-10..70)
	ACCESS  read-only
	STATUS mandatory
	DESCRIPTION
        "This is the temperature of the modem of the IDU in degrees of 
Celsius."
	::= { gnGenStatDeviceEntry 2 }

gnGenStatDeviceFahrenheitTemp OBJECT-TYPE
        SYNTAX  INTEGER (14..158)
	ACCESS  read-only
	STATUS mandatory
	DESCRIPTION
        "This is the temperature of the modem of the IDU in degrees of 
Fahrenheit."
	::= { gnGenStatDeviceEntry 3 }

gnGenStatDevicePowerSupply OBJECT-TYPE
	SYNTAX OCTET STRING(SIZE(1))
	ACCESS  read-only
	STATUS mandatory
	DESCRIPTION
	"This octet represents the status of the power
	supplies of the IDU:
	bit 1 on = 3.3V faulty
	bit 2 on = -5V faulty
	bit 3 on = 5V faulty.
      bit 4 on = +8V faulty "

	::= { gnGenStatDeviceEntry 4 }

gnGenStatDeviceCable OBJECT-TYPE
	SYNTAX  INTEGER {
		ok(2),
		short(3),
		open(4)
	}
	ACCESS  read-only
	STATUS mandatory
	DESCRIPTION
	"Status of the cable to the ODU."
	::= { gnGenStatDeviceEntry 5 }


gnGenStatDeviceDryContact OBJECT-TYPE
	SYNTAX OCTET STRING(SIZE(2))
	ACCESS  read-only
	STATUS mandatory
	DESCRIPTION
	"The status of the dry contacts, Each input status is represented by a bit.
	 When the input is on, the bit value is 0.When the input is off, the bit 
value is 1.
	 The MSB represents external alarm 8. For example when only external alarm 
1 is
	 on the status value will be 0xFE00"
	::= { gnGenStatDeviceEntry 6 }

gnGenStatDeviceLeds OBJECT-TYPE
	SYNTAX OCTET STRING(SIZE(3))
	ACCESS  read-only
	STATUS mandatory
	DESCRIPTION
	"The status of the IDU front panel LEDs. For the management station use. "
	::= { gnGenStatDeviceEntry 7 }

gnGenStatInternalCommunication  OBJECT-TYPE
	SYNTAX  OCTET STRING (SIZE(1))
	ACCESS  read-only
	STATUS mandatory
	DESCRIPTION
	"The status of internal communication problem
	 bit 1 = 1: between main CPU and ODU CPU.
	 bit 2 = 1: between main CPU and MUX CPU.
	 bit 3 = 1: between master main CPU and slave main CPU."
	::= { gnGenStatDeviceEntry 8 }

gnGenStatDeviceFanStatus  OBJECT-TYPE
	SYNTAX  OCTET STRING (SIZE(1))
	ACCESS  read-only
	STATUS mandatory
	DESCRIPTION
	"The status of the IDU fans 1 and 2.
	 bit 1 = IDU Fan1 is faulty.
	 bit 2 = IDU Fan2 is faulty."
	::= { gnGenStatDeviceEntry 9 }

gnGenStatDeviceODUStatus  OBJECT-TYPE
	SYNTAX  OCTET STRING (SIZE(2))
	ACCESS  read-only
	STATUS mandatory
	DESCRIPTION
        "ODU status reported with this parameter.
	 Bit1 is MSB. The bit is set when a fault occurs.
	 The bit is cleared when the fault clears.
	 bit 1 = Power Supply status
	 bit 2 = Synthesizer lock status
	 bit 3 = Tx level status
	 bit 4 = ATPC status
	 bit 5 = Rx level status
	 bit 6 = Not currently used.
	 bit 7 = Temperature status
	 bit 8 = Not currently used.
	 bit 9 = ODU loopback status.
	 bit 10 = Internal use (by application).
	 bit 11 = Tx is in Mute.

	 "
	::= { gnGenStatDeviceEntry 10 }

gnGenStatDeviceIDUStatus  OBJECT-TYPE
	SYNTAX  OCTET STRING (SIZE(3))
	ACCESS  read-only
	STATUS mandatory
	DESCRIPTION
        "IDU status reported with this parameter. Bit1 is MSB.
	 The bit is set when a fault occurs. The bit is
          cleared when the fault clears.

	 bit 1  = Power status -
	 bit 2  = Cable open status -
	 bit 3  = Cable short status -
	 bit 4  = Modem Lock status
	 bit 5  = Temperature status
	 bit 6  = Not currently used.
	 bit 7  = loopback status
	 bit 8  = External alarm 1 status
	 bit 9  = External alarm 2 status
	 bit 10 = External alarm 3 status
	 bit 11 = External alarm 4 status
	 bit 12 = External alarm 5 status
	 bit 13 = External alarm 6 status
	 bit 14 = External alarm 7 status
	 bit 15 = External alarm 8 status
	 bit 16 = Remote connectivity status.
	 bit 17 = Inner communication status.
	 bit 18 = Link ID mismatch status.
	 bit 19 = Configuration mismatch status.
	 "
	::= { gnGenStatDeviceEntry 11 }

gnGenStatDeviceRSTStatus  OBJECT-TYPE
	SYNTAX  OCTET STRING (SIZE(2))
	ACCESS  read-only
	STATUS mandatory
	DESCRIPTION
        "The bit is set when a fault occurs. The bit is
          cleared when the fault clears.

	 bit 1 = Line loss of frame status
	 bit 2 = Radio loss of frame status
	 bit 3 = Line  EXC status
	 bit 4 = Radio EXC status
	 bit 5 = Line  SD status
	 bit 6 = Radio SD status
	 bit 7 = loss of signal status
	 bit 8 = J0 mismatch.
	 bit 9 = Line UNE status.
	 "
	::= { gnGenStatDeviceEntry 12 }


gnGenChannelBandwidth OBJECT-TYPE
	SYNTAX  INTEGER
	ACCESS  read-only
	STATUS mandatory
	DESCRIPTION
	"The TX channel bandwidth, displayed in 1/100 MHz.
	For example:
	An STM-1 ETSI TX channel bandwidth of 56MHz is displayed as the value 5600."
	::= { gnGeneral 10 }

gnGenTxFreqNumLocalRemote OBJECT-TYPE
	SYNTAX  INTEGER
	ACCESS  read-write
	STATUS mandatory
	DESCRIPTION
	"Indicates the radio transmit frequency, displayed in
	1/100 MHz. WRITE changes the local and remote sides. Only for systems that 
	support	frequency configuration (Not channel)."
	::= { gnGeneral 11}

gnGenProtocolType OBJECT-TYPE
	SYNTAX  INTEGER {
		gnSDH(2),
              	gnSONET(3),
              	gnSONET-C(4),
				gnSDH-C(5)	--SDH-concatenated for plex6200 (stm4)
	}
	ACCESS  read-write
	STATUS mandatory
	DESCRIPTION
	"This is the radio mapping protocol. -C represents 'concatenated'.  "
	::= { gnGeneral 12}

gnGenLinkId OBJECT-TYPE
        SYNTAX INTEGER (0..65535)
        ACCESS  read-write
        STATUS mandatory
		DESCRIPTION
		"0 for 'old' system that doesn't support the link ID.
		the user can enter values from 1 to 65535"
	    DEFVAL	{0}
        ::= { gnGeneral 13 }

gnGenMibVersion OBJECT-TYPE
		SYNTAX  DisplayString (SIZE(0..15))
        ACCESS  read-only
        STATUS mandatory
		DESCRIPTION
		"The current software version supports this MIB version (and the previous MIB versions)."
        ::= { gnGeneral 14 }

gnGenModemType OBJECT-TYPE
	SYNTAX  INTEGER {
				gn16QAM(2),
             	gn32QAM(3),
              	gn128QAM(4)
		}
        ACCESS  read-only
        STATUS mandatory
		DESCRIPTION
		"The system modem type."
        ::= { gnGeneral 15 }

gnGenRadioSide OBJECT-TYPE
	SYNTAX  INTEGER {
				east(2),
             	west(3)
		}
        ACCESS  read-write
        STATUS mandatory
	    DEFVAL	{east}
        ::= { gnGeneral 16 }

gnGenSystemWorkTime OBJECT-TYPE
	SYNTAX  INTEGER
        ACCESS  read-write
        STATUS mandatory
		DESCRIPTION
		"The System Work Time (hours)."
	    DEFVAL	{0}
        ::= { gnGeneral 17 }

gnGenRxFreqNumLocalRemote OBJECT-TYPE
	SYNTAX  INTEGER
	ACCESS  read-write
	STATUS mandatory
	DESCRIPTION
	"Indicates the radio receive frequency, displayed in
	1/100 MHz. WRITE changes the local and remote sides. Only for systems that 
	support	frequency configuration (Not channel)."
	::= { gnGeneral 18}

gnGenLastCfgTimeandDate OBJECT-TYPE
	SYNTAX OCTET STRING(SIZE(8))
	ACCESS  read-write
	STATUS mandatory
	DESCRIPTION
	"This parameter specifies the last configuration change time and date
          Format 'YYYY-MM-DD,HH:MM:SS' (Hexadecimal).
            A date-time specification.

            field  octets  contents                  range
            -----  ------  --------                  -----
              1      1-2   year                      0..65536
              2       3    month                     1..12
              3       4    day                       1..31
              4       5    hour                      0..23
              5       6    minutes                   0..59
    	      6       7    seconds                   0..60
                           (use 60 for leap-second)
              7       8    deci-seconds              0..9
              8       9    direction from UTC        '+' / '-'
              9      10    hours from UTC            0..11
             10      11    minutes from UTC          0..59

            For example, Tuesday May 26, 1992 at 1:30:15 PM EDT
            would be displayed as:	07 c8 05 1a 0d 1e 0f 00
								  ( 1992 -5 -26,13:30:15 )

            Note that if only local time is known, then timezone
            information (fields 8-10) is not present."
	::= { gnGeneral 19 }

gnGenMostSevereAlarm OBJECT-TYPE
	SYNTAX  INTEGER {
		clear		(0),
		event		(1),
		warning		(3),
		minor		(7),
		major		(15),
		critical	(31)
	}
	ACCESS  read-only
	STATUS mandatory
	DESCRIPTION
	"This parameter specifies the current moset severe alarm in the system."
	::= { gnGeneral 20 }

-- gnGeneral 21-23 are saved for phos.

gnGenAddAlarmExtToTraps OBJECT-TYPE
	SYNTAX  INTEGER {
		no		(2),
		yes		(3)
	}
	ACCESS  read-write
	STATUS mandatory
	DESCRIPTION
	"If chose 'yes', the Origin, Unit, Time_T and Alarm Id from gnAgnCurrentAlarmTable
	 will be bind to the end of each ceragon private trap."
	DEFVAL { no }
	::= { gnGeneral 24 }






-- This group should contain all the MIB support for
-- Managers table, Trap masks and so on...
gnAgn  OBJECT IDENTIFIER ::= { gnSystem 2}

gnAgnMgrTable  OBJECT-TYPE
        SYNTAX  SEQUENCE OF GnAgnMgrEntry
        ACCESS  not-accessible
        STATUS mandatory
        DESCRIPTION
        "This table indicates the managers list that will receive traps."
        ::= { gnAgn 1 }

gnAgnMgrEntry OBJECT-TYPE
        SYNTAX GnAgnMgrEntry
        ACCESS  not-accessible
        STATUS mandatory
	  DESCRIPTION
	  "Entry containing the managers IP addresses and the trap filter 
options."
        INDEX { gnAgnMgrId}
        ::= { gnAgnMgrTable 1 }

GnAgnMgrEntry ::=
            SEQUENCE {
	gnAgnMgrId
             INTEGER,
       	gnAgnMgrIP
       	     IpAddress,
	gnAgnMgrAlarmGroupMask
	     OCTET STRING,
	gnAgnMgrSeverityFilter
	     OCTET STRING,
	gnAgnMgrTrapPort
		INTEGER
    }

gnAgnMgrId OBJECT-TYPE
	SYNTAX  INTEGER
        ACCESS  read-only
   	STATUS mandatory
        DESCRIPTION
              "This value indicates an index of a specific manager"
        ::= { gnAgnMgrEntry 1 }

gnAgnMgrIP OBJECT-TYPE
        SYNTAX  IpAddress
        ACCESS  read-write
	STATUS mandatory
        DESCRIPTION
        "This value indicates the  managers IP address.
	   WRITE an IP address of all zeroes (0.0.0.0) will remove the entry. "
        ::= { gnAgnMgrEntry 2 }


gnAgnMgrAlarmGroupMask OBJECT-TYPE
	SYNTAX  OCTET STRING (SIZE(2))
        ACCESS  read-write
        STATUS mandatory
        DESCRIPTION
      	"bit mask .1 is 'send a trap' 0 is 'dont send a trap'.
         The list of alarms from MSB to LSB is:
         bit 1 = Power Supply Alarm
      	 bit 2 = Cable Alarm
		 bit 3 = Temperature Alarm
		 bit 4 = External Alarm
		 bit 5 = Radio Alarm
		 bit 6 = Modem Alarm
		 bit 7 = Line Alarm
		 bit 8 = SDH Alarm
		 bit 9 = BER Alarm
		 bit 10 = System fault Alarm
		 bit 11 = Maintenance Alarm
		 If this field is 0, only standard traps will be sent to the manager"
        ::= { gnAgnMgrEntry 3 }

gnAgnMgrSeverityFilter OBJECT-TYPE
	SYNTAX  OCTET STRING (SIZE(1))
        ACCESS  read-write
        STATUS mandatory
        DESCRIPTION
      	"This is a bit mask value for masking traps according to its severity.
      	 There is a bit for each severity. If the relevant bit is on (1), then 
		 the Agent will send traps with this severity, and it won't send if the
		 bit is off (0).
         The list of bits from LSB to MSB:
         bit 1 (LSB) = Event.
         bit 2       = Warning.
         bit 3       = Minor.
		 bit 4       = Major.
		 bit 5 (MSB) = Critical."
        ::= { gnAgnMgrEntry 4 }

gnAgnMgrTrapPort	OBJECT-TYPE
	SYNTAX  INTEGER (70..65535)
        ACCESS  read-write
        STATUS mandatory
        DESCRIPTION
      	"The Port for sending the trap for each manager (possible values: 70-65535)"
		DEFVAL { 162 }
        ::= { gnAgnMgrEntry 5 }



gnAgnLogFileData  OBJECT IDENTIFIER  ::= { gnAgn 2 }

gnAgnLogFileMaxEntries OBJECT-TYPE
	SYNTAX  INTEGER
        ACCESS  read-only
   	STATUS mandatory
        DESCRIPTION
              "The maximum number of entries. "
        ::= { gnAgnLogFileData 1 }

gnAgnLogFileValidEntries OBJECT-TYPE
	SYNTAX  INTEGER
        ACCESS  read-only
   	STATUS mandatory
        DESCRIPTION
              "This is the number of valid entries in the current logfile.
               When this value exceeds 70% of capacity (100 entries),
               the management station should store the file in its hard 
disk.
			   If the management station is not active, the MIB will display up to 
100
			   recent logfile events"
        ::= { gnAgnLogFileData 2 }

gnAgnLogFileAction OBJECT-TYPE
	SYNTAX  INTEGER {
		clear(2),
		save(3),
		saveAndClear(4),
		noAction(5)
	}
	ACCESS  read-write
	STATUS mandatory
	DESCRIPTION
	"This attribute allows for logfile actions,
	CLEARing the logfile and/or SAVING the logfile."
	DEFVAL { noAction }
        ::= { gnAgnLogFileData 3 }


gnAgnLogFileTable  OBJECT-TYPE
        SYNTAX  SEQUENCE OF GnAgnLogFileEntry
        ACCESS  not-accessible
        STATUS mandatory
        DESCRIPTION
        "This table is the agents alarm and event log file."
        ::= { gnAgnLogFileData 4 }

gnAgnLogFileEntry OBJECT-TYPE
        SYNTAX GnAgnLogFileEntry
        ACCESS  not-accessible
        STATUS mandatory
	  DESCRIPTION
	  "Entry containing the agents alarm and event log file."
        INDEX { gnAgnLogFileId}
        ::= { gnAgnLogFileTable 1 }

GnAgnLogFileEntry ::=
            SEQUENCE {
	gnAgnLogFileId
             INTEGER,
	gnAgnLogFileValid
             INTEGER,
       	gnAgnLogFileDate
       	     DisplayString,
	gnAgnLogFileTime
      	      DisplayString,
	gnAgnLogFileSeverity
	      INTEGER,
	gnAgnLogFileText
	     DisplayString,
	gnAgnLogFileDeviceCelsiusTemp
	     INTEGER,
	gnAgnLogFileDevicePowerSupply
	     OCTET STRING,
	gnAgnLogFileInternalCommunication
	     OCTET STRING,
        gnAgnLogFileDeviceFanStatus
	     OCTET STRING,
	gnAgnLogFileDeviceODUStatus
	     OCTET STRING,
	gnAgnLogFileDeviceIDUStatus
	     OCTET STRING,
	gnAgnLogFileOduCelsiusTemp
	  INTEGER,
    	gnAgnLogFileOduReceiveLevel
      	   INTEGER,
	gnAgnLogFileOduSynthesizerVCOLock
	     OCTET STRING,
	gnAgnLogFileOduPowerSupply
	     OCTET STRING,
	gnAgnLogFileLineBERCur
	     INTEGER,
	gnAgnLogFileRadioBERCur
	     INTEGER,
	gnAgnLogFileModStatus
	     INTEGER,
	gnAgnLogFileDemodStatus
	     INTEGER,
	gnAgnLogFileLastDemodDefectBlocks
	     INTEGER,
	gnAgnLogFileLastDemodBytesCorrected
	     INTEGER,
	gnAgnLogFileLastDemodBlocksCorrected
	     INTEGER
    }

gnAgnLogFileId OBJECT-TYPE
	SYNTAX  INTEGER
        ACCESS  read-only
   	STATUS mandatory
        DESCRIPTION
              "This value indicates the index of an alarm logfile entry. 
Entry 1 is the most recent logfile
			  event"
        ::= { gnAgnLogFileEntry 1 }

gnAgnLogFileValid OBJECT-TYPE
	SYNTAX  INTEGER { valid(2), notvalid(3) }
        ACCESS  read-only
   	STATUS mandatory
        DESCRIPTION
              "This value indicates the validity of the indexed alarm logfile entry.
			   a VALID log entry is (2) and an INVALID entry is (3)."
        ::= { gnAgnLogFileEntry 2 }

gnAgnLogFileDate OBJECT-TYPE
        SYNTAX  DisplayString
        ACCESS  read-only
	STATUS mandatory
        DESCRIPTION
        "This field is the date the alarm occurred, formatted as YYYY-MM-DD.
	   YYYY represents the year, MM the month and DD -the day. "
        ::= { gnAgnLogFileEntry 3 }


gnAgnLogFileTime OBJECT-TYPE
	SYNTAX  DisplayString
        ACCESS  read-only
        STATUS mandatory
        DESCRIPTION
        "This field is the hour the alarm occurred - format HH:MM.
         HH - Hour, MM - minute"
        ::= { gnAgnLogFileEntry 4 }

gnAgnLogFileSeverity OBJECT-TYPE
       SYNTAX INTEGER {
		event(1),
		warning(3),
		minor(7),
		major(15),
		critical(31)
		}
       ACCESS  read-only
       STATUS  mandatory
       DESCRIPTION
              "This value indicates the severity of the alarm,
                31 for CRITICAL, 15 for MAJOR, 7 for MINOR, 3 for WARNING and 1 for EVENT. "
        ::= { gnAgnLogFileEntry 5 }

gnAgnLogFileText OBJECT-TYPE
	SYNTAX  DisplayString
        ACCESS  read-only
        STATUS mandatory
        DESCRIPTION
        "This field describes the alarm that occurred. Max length 40 
characters."
        ::= { gnAgnLogFileEntry 6 }

gnAgnLogFileDeviceCelsiusTemp OBJECT-TYPE
	SYNTAX  INTEGER
	ACCESS  read-only
	STATUS mandatory
	DESCRIPTION
	"This is the temperature of the IDU in degrees Celsius,
	during the alarm acceptance. "
	::= {gnAgnLogFileEntry 7 }


gnAgnLogFileDevicePowerSupply OBJECT-TYPE
	SYNTAX OCTET STRING(SIZE(1))
	ACCESS  read-only
	STATUS mandatory
	DESCRIPTION
        "This is the Power supply status of the IDU, during the alarm 
acceptance
	bit 1 on = 3.3V faulty
	bit 2 on = -5V faulty
	bit 3 on = 5V faulty.
        bit 4 on = +8V faulty "
	::= {gnAgnLogFileEntry 8 }



gnAgnLogFileInternalCommunication OBJECT-TYPE
	SYNTAX  OCTET STRING (SIZE(1))
	ACCESS  read-only
	STATUS mandatory
	DESCRIPTION
	"This is the internal communication status of the IDU, during the alarm 
acceptance
	 bit 1 = 1: between main CPU and ODU CPU.
	 bit 2 = 1: between main CPU and MUX CPU.
	 bit 3 = 1: between master main CPU and slave main CPU."
	::= {gnAgnLogFileEntry 9 }

gnAgnLogFileDeviceFanStatus OBJECT-TYPE
	SYNTAX  OCTET STRING (SIZE(1))
	ACCESS  read-only
	STATUS mandatory
	DESCRIPTION
	"This is the Fan status of the IDU, during the alarm acceptance
	 bit 1 = Fan1 is faulty.
	 bit 2 = Fan 2 is faulty."
	::= {gnAgnLogFileEntry 10 }

gnAgnLogFileDeviceODUStatus OBJECT-TYPE
	SYNTAX  OCTET STRING (SIZE(2))
	ACCESS  read-only
	STATUS mandatory
	DESCRIPTION
	"This is the ODU status during the alarm acceptance
         bit 1 MSB
	 bit 1 = Power Supply status
	 bit 2 = Synthesizer lock status
	 bit 3 = Tx level status
	 bit 4 = ATPC status
	 bit 5 = Rx level status
	 bit 6 = Not currently used
	 bit 7 = Temperature status
	 bit 8 = Not currently used.
	 bit 9 = Not currently used"
	::= {gnAgnLogFileEntry 11 }

gnAgnLogFileDeviceIDUStatus OBJECT-TYPE
	SYNTAX  OCTET STRING (SIZE(3))
	ACCESS  read-only
	STATUS mandatory
	DESCRIPTION
	"This is the IDU status during the alarm acceptance
         bit 1 MSB
	 bit 1  = Power status -
	 bit 2  = Cable open status -
	 bit 3  = Cable short status -
	 bit 4  = Modem Lock status
	 bit 5  = Temperature status
	 bit 6  = Not currently used.
	 bit 7  = loopback status
	 bit 8  = External alarm 1 status
	 bit 9  = External alarm 2 status
	 bit 10 = External alarm 3 status
	 bit 11 = External alarm 4 status
	 bit 12 = External alarm 5 status
	 bit 13 = External alarm 6 status
	 bit 14 = External alarm 7 status
	 bit 15 = External alarm 8 status
	 bit 16 = Remote connectivity status.
	 bit 17 = Inner communication status.
	 "
	::= {gnAgnLogFileEntry 12 }



gnAgnLogFileOduCelsiusTemp OBJECT-TYPE
	SYNTAX  INTEGER
	ACCESS  read-only
	STATUS mandatory
	DESCRIPTION
	"This is the temperature of the ODU in degrees Celsius,
	during the alarm acceptance."
	::= {gnAgnLogFileEntry 13 }

gnAgnLogFileOduReceiveLevel OBJECT-TYPE
	SYNTAX  INTEGER
	ACCESS  read-only
	STATUS mandatory
	DESCRIPTION
	"This is the received signal level in DBM, during the alarm acceptance "
	::= {gnAgnLogFileEntry 14 }

gnAgnLogFileOduSynthesizerVCOLock OBJECT-TYPE
	SYNTAX  OCTET STRING (SIZE(1))
	ACCESS  read-only
	STATUS mandatory
	DESCRIPTION
	"This is the Synthesizer status, during the alarm acceptance
	bit 1 on = TX IF synthesizer fault
	bit 2 on = RX IF synthesizer fault
	bit 3 on = Xband synthesizer fault
	bit 4 on = History TX IF synthesizer fault
	bit 5 on = History RX IF synthesizer fault
	bit 6 on = History Xband synthesizer fault "
	::= {gnAgnLogFileEntry 15 }

gnAgnLogFileOduPowerSupply OBJECT-TYPE
	SYNTAX  OCTET STRING (SIZE(1))
	ACCESS  read-only
	STATUS mandatory
	DESCRIPTION
	"This is the ODU power supply status, during the alarm acceptance
	bit 1 on = +5V faulty
	bit 2 on = +8V faulty
	bit 3 on = +12V faulty
        bit 4 on = -12V faulty."
	::= {gnAgnLogFileEntry 16 }

gnAgnLogFileLineBERCur OBJECT-TYPE
	SYNTAX  INTEGER
	ACCESS  read-only
	STATUS mandatory
	DESCRIPTION
	"This is the Line BER (Bit Error Rate), during the alarm acceptance.
	Included for future development, not currently supported."
	::= {gnAgnLogFileEntry 17 }

gnAgnLogFileRadioBERCur OBJECT-TYPE
	SYNTAX  INTEGER
	ACCESS  read-only
	STATUS mandatory
	DESCRIPTION
	"This is the Radio BER (Bit Error Rate), during the alarm acceptance.
	 Included for future development, not currently supported."
	::= {gnAgnLogFileEntry 18 }


gnAgnLogFileModStatus OBJECT-TYPE
	SYNTAX  INTEGER
	ACCESS  read-only
	STATUS mandatory
	DESCRIPTION
	"This is the Modulator status, during the alarm acceptance
		ok(2),
		modulatorFault(3)"
	::= {gnAgnLogFileEntry 19 }


gnAgnLogFileDemodStatus OBJECT-TYPE
	SYNTAX  INTEGER
	ACCESS  read-only
	STATUS mandatory
	DESCRIPTION
	"This is the Demodulator status, during the alarm acceptance . This field 
is for Ceragon
	 internal debugging "
	::= {gnAgnLogFileEntry 20 }


gnAgnLogFileLastDemodDefectBlocks OBJECT-TYPE
	SYNTAX  INTEGER
	ACCESS  read-only
	STATUS mandatory
	DESCRIPTION
	"This is the number of the Defected blocks (blocks that couldn't be 
corrected)
         by the FEC, during the alarm acceptance last second."
	::= {gnAgnLogFileEntry 21 }

gnAgnLogFileLastDemodBytesCorrected OBJECT-TYPE
	SYNTAX  INTEGER
	ACCESS  read-only
	STATUS mandatory
	DESCRIPTION
	"This is the number of the bytes that were corrected by the FEC,
	during the alarm acceptance last second."
	::= {gnAgnLogFileEntry 22 }

gnAgnLogFileLastDemodBlocksCorrected OBJECT-TYPE
	SYNTAX  INTEGER
	ACCESS  read-only
	STATUS mandatory
	DESCRIPTION
	"This is the number of the blocks that were corrected by the FEC
         , during the alarm acceptance last second."
	::= {gnAgnLogFileEntry 23 }

gnAgnExternAlarm  OBJECT IDENTIFIER  ::= { gnAgn 3 }
gnAgnInExternAlarmTable   OBJECT-TYPE
        SYNTAX  SEQUENCE OF GnAgnInExternAlarmEntry
        ACCESS  not-accessible
        STATUS mandatory
        DESCRIPTION
        "This table is the input external alarm table. "
        ::= { gnAgnExternAlarm 1 }

gnAgnInExternAlarmEntry OBJECT-TYPE
        SYNTAX GnAgnInExternAlarmEntry
        ACCESS  not-accessible
        STATUS mandatory
	  DESCRIPTION
	  "Entry containing the external alarm inputs."

        INDEX { gnAgnInExternAlarmDevId,gnAgnInExternAlarmIndex}
        ::= { gnAgnInExternAlarmTable   1 }

GnAgnInExternAlarmEntry ::=
            SEQUENCE {
	gnAgnInExternAlarmDevId
             INTEGER,
	gnAgnInExternAlarmIndex
             INTEGER,
	gnAgnInExternAlarmEnable
             INTEGER,
	gnAgnInExternAlarmText
       	     DisplayString,
	gnAgnInExternAlarmSeverity
      	      INTEGER
    }

gnAgnInExternAlarmDevId OBJECT-TYPE
	SYNTAX  INTEGER {
		local(1),
		remote(2)
	}
        ACCESS  read-only
   	STATUS mandatory
        DESCRIPTION
              "This value indicates device to which the external alarm
                is connected - 1 Local, 2 Remote"
        ::= { gnAgnInExternAlarmEntry 1 }

gnAgnInExternAlarmIndex OBJECT-TYPE
        SYNTAX INTEGER(1..8)
        ACCESS  read-only
   	STATUS mandatory
        DESCRIPTION
              "This value indicates the index of the input external alarm
                1 to 8"
        ::= { gnAgnInExternAlarmEntry 2 }

gnAgnInExternAlarmEnable OBJECT-TYPE
	SYNTAX  INTEGER {
		disabled(2),
		enabled(3)
	}
        ACCESS  read-write
   	STATUS mandatory
        DESCRIPTION
              "This value indicates if this Input alarm is enabled."
	DEFVAL { disabled }
        ::= { gnAgnInExternAlarmEntry 3 }


gnAgnInExternAlarmText OBJECT-TYPE
	SYNTAX  DisplayString
        ACCESS  read-write
        STATUS mandatory
        DESCRIPTION
        "This field describes the external alarm. Max string 20 characters"
	DEFVAL {"Alarm Description"}
        ::= { gnAgnInExternAlarmEntry 4 }

gnAgnInExternAlarmSeverity   OBJECT-TYPE
        SYNTAX INTEGER {
			event(1),
			warning(3),
			minor(7),
			major(15)
		}
       ACCESS  read-write
       STATUS  mandatory
       DESCRIPTION
              "This value indicates the severity of the external alarm
                15 MAJOR, 7 MINOR, 3 WARNING and 1 EVENT. "
       DEFVAL { 1}
        ::= { gnAgnInExternAlarmEntry 5 }



gnAgnOutRelayAlarmTable   OBJECT-TYPE
        SYNTAX  SEQUENCE OF GnAgnOutRelayAlarmEntry
        ACCESS  not-accessible
        STATUS mandatory
        DESCRIPTION
        "This table is the output relay alarm table. "
        ::= { gnAgnExternAlarm 2 }

gnAgnOutRelayAlarmEntry OBJECT-TYPE
        SYNTAX GnAgnOutRelayAlarmEntry
        ACCESS  not-accessible
        STATUS mandatory
	  DESCRIPTION
	  "Entry containing the output relay alarms."
        INDEX { gnAgnOutRelayAlarmDevId,gnAgnOutRelayAlarmIndex}
        ::= { gnAgnOutRelayAlarmTable   1 }

GnAgnOutRelayAlarmEntry ::=
            SEQUENCE {
	gnAgnOutRelayAlarmDevId
             INTEGER,
	gnAgnOutRelayAlarmIndex
             INTEGER,
	gnAgnOutRelayAlarmType
      	      INTEGER
    }

gnAgnOutRelayAlarmDevId OBJECT-TYPE
	SYNTAX  INTEGER {
		local(1),
		remote(2)
	}
        ACCESS  read-only
   	STATUS mandatory
        DESCRIPTION
              "This value indicates device from which the relay is sent
                from - 1 Local, 2 Remote"
        ::= { gnAgnOutRelayAlarmEntry 1 }

gnAgnOutRelayAlarmIndex OBJECT-TYPE
        SYNTAX INTEGER(1..5)
        ACCESS  read-only
   	STATUS mandatory
        DESCRIPTION
              "This value indicates the index of the Output Relay alarm
                1 to 5"
        ::= { gnAgnOutRelayAlarmEntry 2 }


gnAgnOutRelayAlarmType   OBJECT-TYPE
	SYNTAX  INTEGER {
				major(2),
                minor(3),
              	warning(4),
                external(5),
              	power(6),
                ber(7),
              	line(8),
                loopback(9),
                lof(10),
				idu(11),
				odu(12),
                cable(13),
              	remote(14),
				critical(15),
				testOn(16),
				off(17)
	}
       ACCESS  read-write
       STATUS  mandatory
       DESCRIPTION
              "This value indicates the alarm/led that causes
                the relay to change its state"
       DEFVAL { major}
        ::= { gnAgnOutRelayAlarmEntry 3 }

-- *******************************************************************

gnAgnFileTransfer  OBJECT IDENTIFIER  ::= { gnAgn 4 }

gnAgnFileTransferDestination  OBJECT-TYPE
	SYNTAX  INTEGER {
	                 gnLocal     				  (1)}
--	                 gnRemote    				  (2)
--					}
	ACCESS  read-write
	STATUS  mandatory
	DESCRIPTION
	"The file destination. The file transfer destination will always be set to 
1, LOCAL. "
	::= { gnAgnFileTransfer 1 }

gnAgnFileTransferServerIP  OBJECT-TYPE
	SYNTAX  IpAddress
	ACCESS  read-write
	STATUS  mandatory
	DESCRIPTION
	"The IP address of the server from which the file is loaded "
	::= { gnAgnFileTransfer 2 }

gnAgnFileTransferFileName  OBJECT-TYPE
	SYNTAX  DisplayString
	ACCESS  read-write
	STATUS  mandatory
	DESCRIPTION
	"The name of the file to be loaded, format 8.3. "
	::= { gnAgnFileTransfer 3 }

gnAgnFileTransferTftpTotalTimeOut OBJECT-TYPE
    SYNTAX  INTEGER
    ACCESS  read-write
    STATUS  mandatory
    DESCRIPTION
        "Receiving time-out value (seconds)."
    -- DEFVAL  { 20 }
    ::= { gnAgnFileTransfer 4 }


gnAgnFileTransferTransCmd  OBJECT-TYPE
	SYNTAX  INTEGER {
	                 gnStartMUXSoftwareDownLoad     (1),
	                 gnStartODUSoftwareDownLoad     (2),
	                 gnStartMainManagerSoftwareDownLoad   (3),
					 gnCancel					(4),
--	                 gnStartMUXSoftwareUpLoad     (4),
--	                 gnStartODUSoftwareUpLoad     (5),
			 gnNoOperation          (255)
					}
	ACCESS  read-write
	STATUS  mandatory
	DESCRIPTION
	"The command to be executed on fileName at fileServerIP."
	::= { gnAgnFileTransfer 5 }


gnAgnFileTransfertFtpStatus OBJECT-TYPE
    SYNTAX  INTEGER {
	                 gnTftpSessionPreStartSession   (1),
	                 gnTftpSessionFileError    (2),
	                 gnTftpSessionRcvBlock     (3),
	                 gnTftpSessionRcvtimeout    (4),
	                 gnTftpSessionRcvError     (5),
					 gnTftpSessionDone          (6),
	                 gnNoTftpSession     (255)
					}
    ACCESS  read-only
    STATUS  mandatory
    DESCRIPTION
        "Tftp session status "
    ::= { gnAgnFileTransfer 6 }

gnAgnFileTransfertftpBlockCount OBJECT-TYPE
    SYNTAX  INTEGER
    ACCESS  read-only
    STATUS  mandatory
    DESCRIPTION
        "The total number of blocks received in the current tFtp session "
    ::= { gnAgnFileTransfer 7 }


--//////////////////////////////////////

gnAgnInternalDownloadTable  OBJECT-TYPE
        SYNTAX  SEQUENCE OF GnAgnInternalDownloadEntry
        ACCESS  not-accessible
        STATUS mandatory
        DESCRIPTION
        "This table controls the Internal Download process
	   from manager to MUX and ODU (local and remote)."
        ::= { gnAgn 5 }

gnAgnInternalDownloadEntry OBJECT-TYPE
        SYNTAX GnAgnInternalDownloadEntry
        ACCESS  not-accessible
        STATUS mandatory
	  DESCRIPTION
	  "Entry containing the internal download process controls, for local and 
remote."
        INDEX { gnAgnInternalDownloadId}
        ::= { gnAgnInternalDownloadTable 1 }

GnAgnInternalDownloadEntry ::=
            SEQUENCE {
	gnAgnInternalDownloadId
             INTEGER,
    gnAgnInternalDownloadOperation
       	     INTEGER,
    gnAgnInternalDownloadAction
       	     INTEGER,
	gnAgnInternalDownloadStatus
		     INTEGER,
    gnAgnInternalDownloadBlockCount
       	     INTEGER
    }

gnAgnInternalDownloadId OBJECT-TYPE
	SYNTAX  INTEGER
    ACCESS  read-only
   	STATUS mandatory
        DESCRIPTION
              "This value indicates an index of a specific Internal Download 
operation."
        ::= { gnAgnInternalDownloadEntry 1 }


gnAgnInternalDownloadOperation OBJECT-TYPE
	SYNTAX  INTEGER {
		localMUX(2),
		localODU(3),
		remoteMUX(4),
		remoteODU(5)
	}
	ACCESS  read-only
	STATUS mandatory
	DESCRIPTION
	"The Operation Description"
        ::= { gnAgnInternalDownloadEntry 2 }

gnAgnInternalDownloadAction OBJECT-TYPE
	SYNTAX  INTEGER { 	start(2),
						cancel(3),
						clear(4),
						noAction(5) }
	ACCESS  read-write
	STATUS mandatory
	DESCRIPTION
	"This parameter controls the download action operation. "
	DEFVAL { noAction}
        ::= { gnAgnInternalDownloadEntry 3 }

gnAgnInternalDownloadStatus OBJECT-TYPE
    SYNTAX  INTEGER {

			 gnInternalDownloadSessionError    		(1),
	 		 gnInternalDownloadSessionClearing 	    (2),
             gnInternalDownloadSessionSendBlock     (3),
             gnInternalDownloadSessiontimeout   	(4),
	 		 gnInternalDownloadSessionDone	 	    (5),
			 gnInternalDownloadSessionWaitForRetransmit (6),	--phos odu
			 gnNoInternalDownloadSession    		(255)

            					}
    ACCESS  read-only
    STATUS  mandatory
    DESCRIPTION
        " Internal download session status "
        ::= { gnAgnInternalDownloadEntry 4 }

gnAgnInternalDownloadBlockCount OBJECT-TYPE
    SYNTAX  INTEGER
    ACCESS  read-only
    STATUS  mandatory
    DESCRIPTION
        "The total number of blocks sent in the current session."
        ::= { gnAgnInternalDownloadEntry 5 }


--//////////////////////////////////////


--//////////////////////////////////////

gnAgnInterLinkTable  OBJECT-TYPE
        SYNTAX  SEQUENCE OF GnAgnInterLinkEntry
        ACCESS  not-accessible
        STATUS mandatory
        DESCRIPTION
        "This table controls the Inter Link Download process
	   between local and remote masters and between master and slave (local or 
remote).
		 Each session transfers MUX, ODU or manager (IDC) software."
        ::= { gnAgn 6 }

gnAgnInterLinkEntry OBJECT-TYPE
        SYNTAX GnAgnInterLinkEntry
        ACCESS  not-accessible
        STATUS mandatory
	  DESCRIPTION
	  "Entry containing the process controls for the interlink download 
process, for local and remote."
        INDEX { gnAgnInterLinkId}
        ::= { gnAgnInterLinkTable 1 }

	GnAgnInterLinkEntry ::=
            SEQUENCE {
	gnAgnInterLinkId
             INTEGER,
	gnAgnInterLinkSide
			 INTEGER,
    gnAgnInterLinkSource
       	     INTEGER,
    gnAgnInterLinkDestination
       	     INTEGER,
    gnAgnInterLinkSoftware
       	     INTEGER,
    gnAgnInterLinkAction
       	     INTEGER,
	gnAgnInterLinkStatus
		     INTEGER,
    gnAgnInterLinkBlockCount
       	     INTEGER
    }

gnAgnInterLinkId OBJECT-TYPE
	SYNTAX  INTEGER
    ACCESS  read-only
   	STATUS mandatory
        DESCRIPTION
              "This value indicates the index of a specific InterLink  
operation."
        ::= { gnAgnInterLinkEntry 1 }

gnAgnInterLinkSide OBJECT-TYPE
	SYNTAX  INTEGER {
		local(2),
		remote(3)
	}
	ACCESS  read-only
	STATUS mandatory
	DESCRIPTION
	"The Link Side "
        ::= { gnAgnInterLinkEntry 2 }


gnAgnInterLinkSource OBJECT-TYPE
	SYNTAX  INTEGER {
		me(2),
		mate(3)
	}
	ACCESS  read-write
	STATUS mandatory
	DESCRIPTION
	"The source distribution center."
        ::= { gnAgnInterLinkEntry 3 }

gnAgnInterLinkDestination OBJECT-TYPE
	SYNTAX  INTEGER {
		me(2),
		mate(3),
                remote(4)
	}
	ACCESS  read-write
	STATUS mandatory
	DESCRIPTION
	"The destination distribution center.
	 The destination may be selected as the local IDU being contacted (me),
	 the collocated local IDU, in a protected configuration (mate) or
	 it may be selected to be the remote IDU."
        ::= { gnAgnInterLinkEntry 4 }

gnAgnInterLinkSoftware OBJECT-TYPE
	SYNTAX  INTEGER {
		manager(2),
		mux(3),
                odu(4)
	}
	ACCESS  read-write
	STATUS mandatory
	DESCRIPTION
	"The software type to be transferred. MUX, ODU or IDU (referred to as 
manager)."
        ::= { gnAgnInterLinkEntry 5 }



gnAgnInterLinkAction OBJECT-TYPE
	SYNTAX  INTEGER { start(2), cancel(3), noAction(4) }
	ACCESS  read-write
	STATUS mandatory
	DESCRIPTION
	"This parameter controls the interlink action operation. "
	DEFVAL { noAction}
        ::= { gnAgnInterLinkEntry 6 }

gnAgnInterLinkStatus OBJECT-TYPE
    SYNTAX  INTEGER {

			 gnInterLinkSessionError    		(1),
	 		 gnInterLinkSessionClearing 	    (2),
             gnInterLinkSessionSendBlock     (3),
             gnInterLinkSessiontimeout   	(4),
	 		 gnInterLinkSessionDone	 	    (5),
			 gnNoInterLinkSession    		(255)

            					}
    ACCESS  read-only
    STATUS  mandatory
    DESCRIPTION
        " Inter-link session status "
        ::= { gnAgnInterLinkEntry 7 }

gnAgnInterLinkBlockCount OBJECT-TYPE
    SYNTAX  INTEGER
    ACCESS  read-only
    STATUS  mandatory
    DESCRIPTION
        "The total number of blocks sent in the current session."
        ::= { gnAgnInterLinkEntry 8 }

--//////////////////////////////////////

gnSoftwareVersionTable  OBJECT-TYPE
        SYNTAX  SEQUENCE OF GnSoftwareVersionEntry
        ACCESS  not-accessible
        STATUS mandatory
        DESCRIPTION
        "This table contains the IDU, MUX & ODU software versions;
         local and remote."
        ::= { gnAgn 7 }

gnSoftwareVersionEntry OBJECT-TYPE
        SYNTAX GnSoftwareVersionEntry
        ACCESS  not-accessible
        STATUS mandatory
	  DESCRIPTION
	  "Entry containing the currently operating IDU, ODU and MUX software 
versions."
        INDEX { gnSoftwareVersionId }
        ::= { gnSoftwareVersionTable 1 }

GnSoftwareVersionEntry ::=
 	SEQUENCE {
	gnSoftwareVersionId
      INTEGER,
	gnSoftwareVersionIDU
	  DisplayString,								
	gnSoftwareVersionMUX
	  DisplayString,
	gnSoftwareVersionODU
	  DisplayString,
	gnSoftwareVersionIDUPostResetVersion
	  DisplayString,
	gnSoftwareVersionMUXPostResetVersion
	  DisplayString,
	gnSoftwareVersionODUPostResetVersion
	  DisplayString,
	gnSoftwareVersionMuxAlteraVer
	  DisplayString

	}

gnSoftwareVersionId OBJECT-TYPE
	SYNTAX  INTEGER {
		local(1),
		remote(2)
	}
    ACCESS  read-only
   	STATUS mandatory
    DESCRIPTION
    "The ID indicates which device is involved
	in the specific row. The software table includes two rows,
	one for the local radio and one for the remote radio."
        ::= { gnSoftwareVersionEntry 1 }

gnSoftwareVersionIDU OBJECT-TYPE
	SYNTAX  DisplayString (SIZE(0..15))
	ACCESS  read-only
	STATUS mandatory
	DESCRIPTION
	"This is the IDU software version."
	::= { gnSoftwareVersionEntry 2 }

gnSoftwareVersionMUX OBJECT-TYPE
	SYNTAX  DisplayString (SIZE(0..15))
	ACCESS  read-only
	STATUS mandatory
	DESCRIPTION
	"This is the MUX software version."
	::= { gnSoftwareVersionEntry 3 }

gnSoftwareVersionODU OBJECT-TYPE
	SYNTAX  DisplayString (SIZE(0..15))
	ACCESS  read-only
	STATUS mandatory
	DESCRIPTION
	"This is the ODU software version."
	::= { gnSoftwareVersionEntry 4 }

gnSoftwareVersionIDUPostResetVersion OBJECT-TYPE
	SYNTAX  DisplayString (SIZE(0..15))
	ACCESS  read-only
	STATUS mandatory
	DESCRIPTION
	"This is the IDU post reset software version."
	::= { gnSoftwareVersionEntry 5 }

gnSoftwareVersionMUXPostResetVersion OBJECT-TYPE
	SYNTAX  DisplayString (SIZE(0..15))
	ACCESS  read-only
	STATUS mandatory
	DESCRIPTION
	"This is the MUX post reset software version."
	::= { gnSoftwareVersionEntry 6 }

gnSoftwareVersionODUPostResetVersion OBJECT-TYPE
	SYNTAX  DisplayString (SIZE(0..15))
	ACCESS  read-only
	STATUS mandatory
	DESCRIPTION
	"This is the ODU post reset software version."
	::= { gnSoftwareVersionEntry 7 }
	
gnSoftwareVersionMuxAlteraVer OBJECT-TYPE
	SYNTAX  DisplayString (SIZE(0..100))
	ACCESS  read-only
	STATUS mandatory
	DESCRIPTION
	"This string contains the MUX altera versions"
	::= { gnSoftwareVersionEntry 8 }


--//////////////////////////////////////

gnAgnNTPCfg  OBJECT IDENTIFIER  ::= { gnAgn 8 }

gnAgnNTPCfgServerIP  OBJECT-TYPE
 	SYNTAX  IpAddress
	ACCESS  read-write
	STATUS  mandatory
	DESCRIPTION
	" The IP address of the server from which
	the current time is loaded."
	::= { gnAgnNTPCfg 1 }

gnAgnNTPCfgOffsetFromUTC  OBJECT-TYPE
 	SYNTAX  INTEGER (-1439..1439)
	ACCESS  read-write
	STATUS  mandatory
	DESCRIPTION
	" The offset from Coordinated Universal Time (minutes).
	Possible values: -1439..1439. "
	DEFVAL	{0}
	::= { gnAgnNTPCfg 2 }

gnAgnNTPCfgSummerAdjOffset  OBJECT-TYPE
	SYNTAX  INTEGER (-1439..1439)
	ACCESS  read-write
	STATUS  mandatory
	DESCRIPTION
	" The summer adjustment offset (minutes).
	Possible values: -1439..1439. "
	DEFVAL	{0}
	::= { gnAgnNTPCfg 3 }

gnAgnNTPCfgSummerAdjStart OBJECT-TYPE
    SYNTAX  INTEGER
    ACCESS  read-write
    STATUS  mandatory
    DESCRIPTION
    " The summertime adjustment start. 
	In order to set this value:
	1.Turn every parameter (month, day, hour, minute)
	  to hexadecimal.
	2.Write them all together - from left to right.
	3.Turn the accepted number to decimal basis.
	For example:
	in order to set 11:27:1:55 --> 11 = 0x0b, 27 = 0x1b,
	1 = 0x01, 55 = 0x37 --> the 4 parameters together:
	0x0b1b0137 = 186319159 (the last number is the one to set)."
    ::= { gnAgnNTPCfg 4 }


gnAgnNTPCfgSummerAdjEnd  OBJECT-TYPE
	SYNTAX  INTEGER 
	ACCESS  read-write
	STATUS  mandatory
	DESCRIPTION
    " The summertime adjustment end. 
	In order to set this value:
	1.Turn every parameter (month, day, hour, minute)
	  to hexadecimal.
	2.Write them all together - from left to right.
	3.Turn the accepted number to decimal basis.
	For example:
	in order to set 11:27:1:55 --> 11 = 0x0b, 27 = 0x1b,
	1 = 0x01, 55 = 0x37 --> the 4 parameters together:
	0x0b1b0137 = 186319159 (the last number is the one to set)."
	::= { gnAgnNTPCfg 5 }

gnAgnNTPCfgEnableAuth OBJECT-TYPE
    SYNTAX  INTEGER {
		disabled(2),
		des(3)
					}
    ACCESS  read-write
    STATUS  mandatory
    DESCRIPTION
    " This value indicates if the Authentication is enabled. "
	DEFVAL	{disabled}
    ::= { gnAgnNTPCfg 6 }

gnAgnNTPCfgAuthSecretKey OBJECT-TYPE
	SYNTAX  OCTET STRING (SIZE(8))
    ACCESS  read-write
    STATUS  mandatory
    DESCRIPTION
    " The authentication secret key (HEX).
	Not relevant when authentication is disable. "
    ::= { gnAgnNTPCfg 7 }

gnAgnNTPCfgAuthPublicKey OBJECT-TYPE
    SYNTAX  Gauge
    ACCESS  read-write
    STATUS  mandatory
    DESCRIPTION
    " The authentication public key is an integer number.
	The valid values: 1-4294967295.
	Not relevant when authentication is disable. "
    ::= { gnAgnNTPCfg 8 }

gnAgnNTPCfgUpdateInterval  OBJECT-TYPE
	SYNTAX  INTEGER (1..65535)
	ACCESS  read-write
	STATUS  mandatory
	DESCRIPTION
	" The time interval between sending NTP requests 
	to the NTP server (minutes). Possible values: 1-65535. "
	DEFVAL	{10}
	::= { gnAgnNTPCfg 9 }

gnAgnNTPCfgProtocolType OBJECT-TYPE
    SYNTAX  INTEGER {
		ntp(2),
		sntp(3)
					}
    ACCESS  read-write
    STATUS  mandatory
    DESCRIPTION
    "  "
	DEFVAL	{ntp}
    ::= { gnAgnNTPCfg 10 }


gnAgnInBandMng  OBJECT IDENTIFIER  ::= { gnAgn 9 }

gnAgnInBandMngEthernetIp  OBJECT-TYPE
 	SYNTAX  IpAddress
	ACCESS  read-only
	STATUS  mandatory
	DESCRIPTION
	" The ethernet IP of the gateway network element."
	::= { gnAgnInBandMng 1 }

gnAgnInBandMngEthernetMask  OBJECT-TYPE
 	SYNTAX  IpAddress
	ACCESS  read-write
	STATUS  mandatory
	DESCRIPTION
	" The IP mask of the gateway network element."
	::= { gnAgnInBandMng 2 }

gnAgnInBandMngPppIp  OBJECT-TYPE
 	SYNTAX  IpAddress
	ACCESS  read-only
	STATUS  mandatory
	DESCRIPTION
	" The PPP IP address of the gateway network element."
	::= { gnAgnInBandMng 3 }

gnAgnInBandMngPppMask  OBJECT-TYPE
 	SYNTAX  IpAddress
	ACCESS  read-write
	STATUS  mandatory
	DESCRIPTION
	" The PPP IP mask of the gateway network element."
	::= { gnAgnInBandMng 4 }

gnAgnInBandMngDefRoute  OBJECT-TYPE
 	SYNTAX  IpAddress
	ACCESS  read-write
	STATUS  mandatory
	DESCRIPTION
    " The IP address of the default gateway/router
	to the internet. "
	::= { gnAgnInBandMng 5 }

gnAgnInBandMngEnable  OBJECT-TYPE
	SYNTAX  INTEGER {
			enable(2),
			disable(3)
	}
	ACCESS  read-write
	STATUS  mandatory
	DESCRIPTION
	" Enable/Disable in-band management."
	::= { gnAgnInBandMng 6 }

gnAgnInBandMngNetworkElementType  OBJECT-TYPE
	SYNTAX  INTEGER {
			networkElement(2),
			gateway(3)
	}
	ACCESS  read-write
	STATUS  mandatory
	DESCRIPTION
	" The element type of a single unit on the  
	inband network (Gateway or Network Element). "
	::= { gnAgnInBandMng 7 }

gnAgnInBandMngRadioChannel  OBJECT-TYPE
	SYNTAX  INTEGER {
			dccr(2),
			dccm(3),
			mediaSpecific128k(4),
			proprietary(5),
			userChannel(6)
	}
	ACCESS  read-write
	STATUS  mandatory
	DESCRIPTION
	" The channel the in-band-management goes over  
	(DCCR\DCCM\etc.). "
	::= { gnAgnInBandMng 8 }

gnAgnInBandMngUnknownPackets  OBJECT-TYPE
	SYNTAX  INTEGER {
			transparent(2),
			discard(3)
	}
	ACCESS  read-write
	STATUS  mandatory
	DESCRIPTION
	" Select if unknown packets will be transparently  
	transmitted over the RING or discarded and dropped."
	::= { gnAgnInBandMng 9 }

gnAgnInBandMngTTL  OBJECT-TYPE
	SYNTAX  INTEGER  (5..64)
	ACCESS  read-write
	STATUS  mandatory
	DESCRIPTION
	" Time To Live."
	::= { gnAgnInBandMng 10 }

gnAgnInBandMngRingIpSubnet  OBJECT-TYPE
 	SYNTAX  IpAddress
	ACCESS  read-write
	STATUS  mandatory
	DESCRIPTION
	" The IP subnet address of the ring."
	::= { gnAgnInBandMng 11 }

gnAgnInBandMngRingIpMask  OBJECT-TYPE
 	SYNTAX  IpAddress
	ACCESS  read-write
	STATUS  mandatory
	DESCRIPTION
	" The IP mask of the ring subnet address."
	::= { gnAgnInBandMng 12 }

gnAgnInBandMngNetworkId  OBJECT-TYPE
 	SYNTAX  INTEGER  (1..255)
	ACCESS  read-write
	STATUS  mandatory
	DESCRIPTION
	" Identification for single link path of  
	PPPoE over cross-networks. "
	::= { gnAgnInBandMng 13 }

gnAgnInBandMngLineMode  OBJECT-TYPE
	SYNTAX  INTEGER {
			inbandFiber(2),
			forcePPPoE(3)
	}
	ACCESS  read-write
	STATUS  mandatory
	DESCRIPTION
	" Enable the user to force PPPoE mode  
	instead of DCCR line communication. "
	::= { gnAgnInBandMng 14 }

gnAgnInBandMngFiberChannel  OBJECT-TYPE
	SYNTAX  INTEGER {
			dccr(2),
			dccm(3),
--			mediaSpecific128k(4),
			userChannel(5)
	}
	ACCESS  read-write
	STATUS  mandatory
	DESCRIPTION
		" "
	DEFVAL { dccr}
	::= { gnAgnInBandMng 15 }

gnAgnInBandMngTribChannel  OBJECT-TYPE
	SYNTAX  INTEGER {
			disable(2),
			dccr(3),
			dccm(4)
	}
	ACCESS  read-write
	STATUS  mandatory
	DESCRIPTION
		" "
	DEFVAL { dccr}
	::= { gnAgnInBandMng 16 }

--//////////////////////////////////////

gnNeighborIP  OBJECT IDENTIFIER  ::= { gnAgn 10 }
gnNeighborInBandTable OBJECT-TYPE
	SYNTAX  SEQUENCE OF GnNeighborInBandEntry
	ACCESS  not-accessible
	STATUS mandatory
	DESCRIPTION
	"This table defines the IP addresses of the units that are connected Inband."
	::= { gnNeighborIP 1 }

gnNeighborInBandEntry OBJECT-TYPE
	SYNTAX GnNeighborInBandEntry
	ACCESS  not-accessible
	STATUS mandatory
	DESCRIPTION
	"This is an entry in the IP addresses of the units that are connected Inband.
	This table contains a row for every interface which type is logically connected.
	for example regenerator which is connected in band has two neighbors: the first (index 1)
      the remote radio unit and the second the remote fiber neighbor (index 2)."
	INDEX {  ifIndex }
	::= { gnNeighborInBandTable 1 }

GnNeighborInBandEntry ::=
	    SEQUENCE {
      	gnNeighborInBandIP  
 	      IpAddress,
        gnNeighborInBandStatus
			INTEGER
    }

gnNeighborInBandIP  OBJECT-TYPE
 	SYNTAX  IpAddress
	ACCESS  read-write
	STATUS  mandatory
	DESCRIPTION
	" The PPP IP address of the gateway network element."
	::= { gnNeighborInBandEntry 1 }

gnNeighborInBandStatus OBJECT-TYPE
	SYNTAX  INTEGER {
		up(2),
		down(3),
		closed(4)
	}
   	ACCESS  read-only
   	STATUS mandatory
   	DESCRIPTION
    "."
    ::= { gnNeighborInBandEntry 2 }



gnNeighborMateIP OBJECT-TYPE
	SYNTAX  IpAddress
	ACCESS  read-only
	STATUS  mandatory
	DESCRIPTION
	" The Protection Mate IP address."
	::= { gnNeighborIP 2 }

gnNeighborRemoteRadioIP OBJECT-TYPE
	SYNTAX  IpAddress
	ACCESS  read-only
	STATUS  mandatory
	DESCRIPTION
	" The IP address of the Radio Remote IDU."
	::= { gnNeighborIP 3 }

-- gnNeighborInBandXEntry is used in Phos.
gnNeighborInBandXTable OBJECT-TYPE
	SYNTAX  SEQUENCE OF GnNeighborInBandXEntry
	ACCESS  not-accessible
	STATUS mandatory
	DESCRIPTION
	"This table defines the IP addresses of the units that are connected Inband."
	::= { gnNeighborIP 4 }

gnNeighborInBandXEntry OBJECT-TYPE
	SYNTAX GnNeighborInBandXEntry
	ACCESS  not-accessible
	STATUS mandatory
	DESCRIPTION
	"This is an entry in the IP addresses of the units that are connected Inband.
	This table contains a row for every interface which type is logically connected.
	for example regenerator which is connected in band has two neighbors: the first (index 1)
      the remote radio unit and the second the remote fiber neighbor (index 2)."
	INDEX {  gnNeighborInBandXId }
	::= { gnNeighborInBandXTable 1 }

GnNeighborInBandXEntry ::=
	    SEQUENCE {
		gnNeighborInBandXId
			INTEGER,
      	gnNeighborInBandXIP
 	      IpAddress
    }

gnNeighborInBandXId OBJECT-TYPE
	SYNTAX  INTEGER
	{
		drawer1(3),
		drawer2(4)
	}
    ACCESS  read-only
   	STATUS mandatory
    DESCRIPTION
    " "
    ::= { gnNeighborInBandXEntry 1 }

gnNeighborInBandXIP  OBJECT-TYPE
 	SYNTAX  IpAddress
	ACCESS  read-write
	STATUS  mandatory
	DESCRIPTION
	" The PPP IP address of the gateway network element."
	::= { gnNeighborInBandXEntry 2 }



gnNeighborIpTable OBJECT-TYPE
	SYNTAX  SEQUENCE OF GnNeighborIpEntry
	ACCESS  not-accessible
	STATUS mandatory
	DESCRIPTION
	"This table shows the Neighbor IP for each STM connection."
	::= { gnNeighborIP 5 }

gnNeighborIpEntry OBJECT-TYPE
	SYNTAX GnNeighborIpEntry
	ACCESS  not-accessible
	STATUS mandatory
	DESCRIPTION
	"."
	INDEX { ifIndex }
	::= { gnNeighborIpTable 1 }

GnNeighborIpEntry ::=
	    SEQUENCE {
        gnNeighborIpDetectMode
			INTEGER,
      	gnNeighborIpAddress  
 	      IpAddress,
        gnNeighborIpRemoteIfIndex
			INTEGER
    }

gnNeighborIpDetectMode OBJECT-TYPE
	SYNTAX  INTEGER {
		disable(2),
		manual(3),
		auto(4)
	}
   	ACCESS  read-write
   	STATUS mandatory
   	DESCRIPTION
    "The Neighbor detect can be done automatically or to be manually insreted.
    Disable marks that the IP Detect is not used."
    ::= { gnNeighborIpEntry 1 }

gnNeighborIpAddress OBJECT-TYPE
 	SYNTAX  IpAddress
	ACCESS  read-write
	STATUS  mandatory
	DESCRIPTION
	"The neighbor IP address."
	::= { gnNeighborIpEntry 2 }

gnNeighborIpRemoteIfIndex OBJECT-TYPE
	SYNTAX  INTEGER 
   	ACCESS  read-write
   	STATUS mandatory
   	DESCRIPTION
    "The If index of the neighbor IP address connected to the current If Index."
    ::= { gnNeighborIpEntry 3 }



gnAgnSNMPCfg  OBJECT IDENTIFIER  ::= { gnAgn 11 }

gnAgnSNMPCfgTrapCommunity  OBJECT-TYPE
	SYNTAX OCTET STRING(SIZE(12))				   
	ACCESS  read-write
	STATUS  mandatory
	DESCRIPTION
	" "
	::= { gnAgnSNMPCfg 1 }

gnAgnSNMPCfgReadCommunity  OBJECT-TYPE
	SYNTAX OCTET STRING(SIZE(12))				   
	ACCESS  read-write
	STATUS  mandatory
	DESCRIPTION
	" "
	::= { gnAgnSNMPCfg 2 }

gnAgnSNMPCfgWriteCommunity  OBJECT-TYPE
	SYNTAX OCTET STRING(SIZE(12))				   
	ACCESS  read-write
	STATUS  mandatory
	DESCRIPTION
	" "
	::= { gnAgnSNMPCfg 3 }


gnAgnPrvt  OBJECT IDENTIFIER  ::= { gnAgn 12 }

gnAgnPrvtCmd  OBJECT-TYPE
	SYNTAX  INTEGER {
		noOperation(2),
        cNV(3),
		cNVBtr(4)
	}
	ACCESS  read-write
	STATUS  mandatory
	DESCRIPTION
	" ."
	DEFVAL { noOperation }
	::= { gnAgnPrvt 1 }

gnAgnPrvtCmdStat  OBJECT-TYPE
	SYNTAX  INTEGER {
		ready(2),
        cNVPass(3),
		cNVFail(4),
		cNVBtrPass(5),
		cNVBtrFail(6)
	}
	ACCESS  read-only
	STATUS  mandatory
	DESCRIPTION
	" ."
	DEFVAL { ready }
	::= { gnAgnPrvt 2 }


-- gnAgn 13 is a space for: gnSoftwareDrawerVersionTable  OBJECT-TYPE  ::= { gnAgn 13 }

-- @@@@@@@@@@@@@@@@@@@@@@@@@@@@@@@@@@@@@@@@@@@@@@@@@@@@@@@@@@@@@@@@@

gnAgnCurrentAlarm OBJECT IDENTIFIER  ::= { gnAgn 14 }

gnAgnCurrentAlarmLastChange OBJECT-TYPE
        SYNTAX INTEGER
        ACCESS  read-only
        STATUS mandatory
		DESCRIPTION
		"This counter initialized to 0 after resest, and incremented on each change in the gnAgnCurrentAlarmTable
		(either add or remove of an entery)."
        ::= { gnAgnCurrentAlarm 1 }  

gnAgnCurrentAlarmTable  OBJECT-TYPE
        SYNTAX  SEQUENCE OF GnCurrentAlarmEntry
        ACCESS  not-accessible
        STATUS mandatory
        DESCRIPTION
        "This table includes the currently open alarm (when a RAISED trap is 
          sent, an alarm is added to the table, when a CLEAR trap is sent, 
          the alarm is removed."
        ::= { gnAgnCurrentAlarm 2 } 

gnCurrentAlarmEntry OBJECT-TYPE
        SYNTAX GnCurrentAlarmEntry
        ACCESS  not-accessible
        STATUS mandatory
	  DESCRIPTION
	  "Entry containing the info of a currently RAISED trap."
        INDEX { gnAgnCurrentAlarmCounter }
        ::= { gnAgnCurrentAlarmTable  1 }

GnCurrentAlarmEntry ::=
            SEQUENCE {
   	gnAgnCurrentAlarmCounter
	      INTEGER, 
	gnAgnCurrentAlarmSeverity
	      INTEGER,
	gnAgnCurrentAlarmId
	      INTEGER, 
   	gnAgnCurrentAlarmIfIndex
	      INTEGER, 
   	gnAgnCurrentAlarmOrigin 
	      INTEGER, 
   	gnAgnCurrentAlarmUnit 
	      INTEGER,
   	gnAgnCurrentAlarmTrapID
	      INTEGER,
	gnAgnCurrentAlarmTimeT
          INTEGER,
	gnAgnCurrentAlarmText 
		  DisplayString
} 

  gnAgnCurrentAlarmCounter OBJECT-TYPE
        SYNTAX INTEGER
        ACCESS  read-only
        STATUS mandatory
		DESCRIPTION
		"A running counter of open alarm, the counter is incremented on every new RAISED trap.
		It is cleared after reset."
        ::= { gnCurrentAlarmEntry 1 }


gnAgnCurrentAlarmSeverity OBJECT-TYPE
	SYNTAX  INTEGER
	{
		event		(1),
		warning		(3),
		minor		(7),
		major		(15),
		critical	(31)
	}
        ACCESS  read-only
        STATUS  mandatory
        DESCRIPTION
        "The current Alarm severity"
         ::= { gnCurrentAlarmEntry 2 }

  gnAgnCurrentAlarmId OBJECT-TYPE
        SYNTAX INTEGER
        ACCESS  read-only
        STATUS mandatory
		DESCRIPTION
		"Alarm Identifier (contains alarm type and interface). Same AlarmId for rasie and clear alarms.
		 This counter is (optionaly) attached to each trap."
        ::= { gnCurrentAlarmEntry 3 }

  gnAgnCurrentAlarmIfIndex OBJECT-TYPE
        SYNTAX INTEGER
        ACCESS  read-only
        STATUS mandatory
		DESCRIPTION
		"Interface Index where the alarm occurred, alarms that are
  		 not associated with specific interface will have the following value:
			For IDC related alarms the value is: 	 65001
			For drawer1 related alarms the value is:  65003
			For drawer1 related alarms the value is:  65004"
        ::= { gnCurrentAlarmEntry 4 }

gnAgnCurrentAlarmOrigin OBJECT-TYPE
	SYNTAX  INTEGER {
		idc(2),
		drawer1(3),
		drawer2(4)
	}
	ACCESS  read-only
	STATUS mandatory
		DESCRIPTION
		"The origin drawer of the alarm (if applicable, otherwise it will be idc(2))."
	::= {gnCurrentAlarmEntry 5}

gnAgnCurrentAlarmUnit OBJECT-TYPE
	SYNTAX  INTEGER {
		idc(2),
		odc(3),
		mux(4)
	}
	ACCESS  read-only
	STATUS mandatory
		DESCRIPTION
		"The unit of the alarm."
	::= {gnCurrentAlarmEntry 6}

gnAgnCurrentAlarmTrapID OBJECT-TYPE
        SYNTAX INTEGER 
        ACCESS  read-only
        STATUS mandatory
		DESCRIPTION
		"The ID of the RAISED trap that was sent when this alarm was raised."
        ::= { gnCurrentAlarmEntry 7 }

gnAgnCurrentAlarmTimeT OBJECT-TYPE
        SYNTAX  INTEGER
        ACCESS  read-only
	STATUS mandatory
        DESCRIPTION
        "Timestamp of this alarm, this number is the seconds from midnight 1.1.1970."
        ::= { gnCurrentAlarmEntry 8 }

gnAgnCurrentAlarmText OBJECT-TYPE
	SYNTAX  DisplayString
	ACCESS  read-only
	STATUS mandatory
	DESCRIPTION
	"The alarm display text (same as the text in the sent trap)."
	::= { gnCurrentAlarmEntry 9}


gnNMS OBJECT IDENTIFIER  ::= { gnAgn 15 }


--//////////////////////////////////////

gnUnits OBJECT IDENTIFIER ::= { ceragon 3 }

gnODU OBJECT IDENTIFIER ::=  { gnUnits 1 }

gnOduCfgTable OBJECT-TYPE
	SYNTAX  SEQUENCE OF GnOduCfgEntry
	ACCESS  not-accessible
	STATUS mandatory
	DESCRIPTION
	"This table defines the configuration of the Outdoor part
                of the system."
	::= { gnODU 1 }

gnOduCfgEntry OBJECT-TYPE
	SYNTAX GnOduCfgEntry
	ACCESS  not-accessible
	STATUS mandatory
	DESCRIPTION
	"This is an entry in the ODU Configuration Table. This table
	contains two rows, indexed by ifIndex= 1 for local ODU and
	ifIndex = 101 for remote ODU."
	INDEX {  ifIndex }
	::= { gnOduCfgTable 1 }


GnOduCfgEntry ::=
	    SEQUENCE {
	gnOduCfgTransmitterFrequency
	  INTEGER,
	gnOduCfgRLPerfMonThresh1
	   INTEGER,
	gnOduCfgRLPerfMonThresh2
	   INTEGER,
	gnOduCfgATPCStatus
	    INTEGER,
	gnOduCfgMUTEStatus
	    INTEGER,
	gnOduCfgAntennaType
	    INTEGER,
	gnOduCfgTransmitLevel
	    INTEGER,
	gnOduCfgRealTxFreqNumber
	    INTEGER,
	gnOduCfgRealRxFreqNumber
	    INTEGER,
	gnOduCfgMinTxFreqNumber
	    INTEGER,
	gnOduCfgMaxTxFreqNumber
	    INTEGER,
	gnOduCfgMaxTxLevel
	    INTEGER,
	gnOduCfgRefRsl
	    INTEGER,
	gnOduCfgForceRmtMuteTx
		INTEGER,
	gnOduCfgForceRmtMaxTx
		INTEGER,
	gnOduCfgTLPerfMonThresh1
	   INTEGER,
	gnOduCfgMinRxFreqNumber
	    INTEGER,
	gnOduCfgMaxRxFreqNumber
	    INTEGER,
	gnOduCfgOduLoopSupport
	    INTEGER,
	gnOduCfgOduModel
		INTEGER,
	gnOduCfgFreqPlanStandard
	    DisplayString,
	gnOduCfgFreqDevider
	    INTEGER
    }

gnOduCfgTransmitterFrequency OBJECT-TYPE
	SYNTAX  INTEGER (0..20)
	ACCESS  read-write
	STATUS mandatory
	DESCRIPTION
	"This parameter indicates the radio TX channel number.
	WRITE will change the LOCAL side only.
	Not all radios will support TX frequency change via channel numbers."
	DEFVAL { 1}
	::= { gnOduCfgEntry 1 }

gnOduCfgRLPerfMonThresh1 OBJECT-TYPE
	SYNTAX  INTEGER (-75..-15)
	ACCESS  read-write
	STATUS mandatory
	DESCRIPTION
	"When the Received Level (RL) exceeds this threshold a
	performance monitoring RL1 counter increments."
	DEFVAL { -50}
	::= { gnOduCfgEntry 2}

gnOduCfgRLPerfMonThresh2 OBJECT-TYPE
	SYNTAX  INTEGER (-75..-15)
	ACCESS  read-write
	STATUS mandatory
	DESCRIPTION
	"When the Received Level (RL) exceeds this threshold a
	performance monitoring RL2 counter increments."
	DEFVAL { -70}
	::= { gnOduCfgEntry 3}


gnOduCfgATPCStatus OBJECT-TYPE
	SYNTAX  INTEGER { on(2), off(3) }
	ACCESS  read-write
	STATUS mandatory
	DESCRIPTION
	"This parameter indicates if the ATPC option is enabled or disabled."
	DEFVAL { on}
	::= { gnOduCfgEntry 4}

gnOduCfgMUTEStatus OBJECT-TYPE
	SYNTAX  INTEGER { on(2), off(3) }
	ACCESS  read-write
	STATUS mandatory
	DESCRIPTION
	"This parameter indicates if transmitter will be in mute state.
            (Mute on -> don't transmit) "
	DEFVAL { off}
	::= { gnOduCfgEntry 5 }

gnOduCfgAntennaType OBJECT-TYPE
	SYNTAX  INTEGER { oneFoot(2), twoFeet(3), threeFeet(4), fourFeet(5), 
sixFeet(6) }
	ACCESS  read-write
	STATUS mandatory
	DESCRIPTION
	"This parameter indicates the size of the antenna used
	in the ODU. This attribute will not auto-detect the antenna size.
	It is used for the unfaded RSL calculation feature included in 
CERAGONView."
	DEFVAL { oneFoot }
	::= { gnOduCfgEntry 6 }

gnOduCfgTransmitLevel OBJECT-TYPE
	SYNTAX  INTEGER (-50..30)
	ACCESS  read-write
	STATUS mandatory
	DESCRIPTION
	"This is the transmitter output power level of the signal
	transmitted by the radios, displayed in DBM. "
	::= { gnOduCfgEntry 7 }

gnOduCfgRealTxFreqNumber OBJECT-TYPE
	SYNTAX  INTEGER
	ACCESS  read-write
	STATUS mandatory
	DESCRIPTION
	"Identifies the RF Tx frequency. For 6, 7 and 8 bands the Tx frequency
	resolution is in kHz, for other bands the resolution is in 10kHz.
	If the Tx frequency value is over 4000000 than the band is identified
	as 6, 7 or 8G band."
	::= { gnOduCfgEntry 8 }

gnOduCfgRealRxFreqNumber OBJECT-TYPE
	SYNTAX  INTEGER
	ACCESS  read-write
	STATUS mandatory
	DESCRIPTION
	"Identifies the RF Rx frequency. For 6, 7 and 8 bands the Rx frequency
	resolution is in kHz, for other bands the resolution is in 10kHz.
	If the Rx frequency value is over 4000000 than the band is identified
	as 6, 7 or 8G band."
	::= { gnOduCfgEntry 9}

gnOduCfgMinTxFreqNumber OBJECT-TYPE
	SYNTAX  INTEGER (0..65535)
	ACCESS  read-only
	STATUS mandatory
	DESCRIPTION
	"This the Minimum TX frequency that the ODU can receive - Used by the 
management station."
	::= { gnOduCfgEntry 10 }

gnOduCfgMaxTxFreqNumber OBJECT-TYPE
	SYNTAX  INTEGER (0..65535)
	ACCESS  read-only
	STATUS mandatory
	DESCRIPTION
	"This the Maximum TX frequency that the ODU can receive - Used by the 
management station."
	::= { gnOduCfgEntry 11}

gnOduCfgMaxTxLevel  OBJECT-TYPE
	SYNTAX  INTEGER (0..99)
	ACCESS  read-only
	STATUS mandatory
	DESCRIPTION
	"This is the theoretical maximum level that this ODU unit
	 can transmit."
	::= { gnOduCfgEntry 12 }

gnOduCfgRefRsl OBJECT-TYPE
	SYNTAX  INTEGER (-70..-30)
	ACCESS  read-write
	STATUS mandatory
	DESCRIPTION
	"This is the received level reference, applicable when utilizing ATPC mode;
	 displayed in dBm."
	::= { gnOduCfgEntry 13 }

gnOduCfgForceRmtMuteTx OBJECT-TYPE
	SYNTAX  INTEGER { on(2), off(3) }
	ACCESS  read-write
	STATUS mandatory
	DESCRIPTION
	"When on, this parameter force the transmitter to be in mute state.
            (Mute on -> don't transmit) "
	DEFVAL { off }
	::= { gnOduCfgEntry 14 }

gnOduCfgForceRmtMaxTx OBJECT-TYPE
	SYNTAX  INTEGER (-50..30)
	ACCESS  read-write
	STATUS mandatory
	DESCRIPTION
	"This parameter force the transmitter output power level of the signal
	transmitted by the radio. "
	::= { gnOduCfgEntry 15 }

gnOduCfgTLPerfMonThresh1 OBJECT-TYPE
	SYNTAX  INTEGER (-10..25)
	ACCESS  read-write
	STATUS mandatory
	DESCRIPTION
	"When the Transmitted Level (TL) exceeds this threshold a
	performance monitoring TL1 counter increments."
	DEFVAL { 25 }
	::= { gnOduCfgEntry 16}


gnOduCfgMinRxFreqNumber OBJECT-TYPE
	SYNTAX  INTEGER
	ACCESS  read-only
	STATUS mandatory
	DESCRIPTION
	"This the Minimum RX frequency that the ODU can receive - Used by the 
management station."
	::= { gnOduCfgEntry 17 }

gnOduCfgMaxRxFreqNumber OBJECT-TYPE
	SYNTAX  INTEGER
	ACCESS  read-only
	STATUS mandatory
	DESCRIPTION
	"This the Maximum RX frequency that the ODU can receive - Used by the 
management station."
	::= { gnOduCfgEntry 18}

gnOduCfgOduLoopSupport OBJECT-TYPE
	SYNTAX  INTEGER {
		notSupported(2),
		supported(3)
	}
	ACCESS  read-only
	STATUS mandatory
	DESCRIPTION
	"Indication for loopback support by the connected ODU."
	::= { gnOduCfgEntry 19}

gnOduCfgOduModel OBJECT-TYPE
	SYNTAX  INTEGER {
		unknown(2),
		v2(3),
		v1(4)
	}
	ACCESS  read-only
	STATUS mandatory
	DESCRIPTION
	"."
	::= { gnOduCfgEntry 20}

gnOduCfgFreqPlanStandard OBJECT-TYPE
	SYNTAX  DisplayString (SIZE(0..45))
	ACCESS  read-write
	STATUS mandatory
	DESCRIPTION
	"For the NMS use."
	::= { gnOduCfgEntry 21}


gnOduCfgFreqDevider OBJECT-TYPE
	SYNTAX  INTEGER
	ACCESS  read-only
	STATUS mandatory
	DESCRIPTION
	"Indicates the number with which we should divide the MIB Freq value to get to the actual Freq (100 or 1000) "
	::= { gnOduCfgEntry 22}



-- RO parameters described the state of the ODU.
gnOduStatusTable OBJECT-TYPE
	SYNTAX  SEQUENCE OF GnOduStatusEntry
	ACCESS  not-accessible
	STATUS mandatory
	DESCRIPTION
	"This table defines the status of the Outdoor unit
                of the system."
	::= { gnODU 2 }

gnOduStatusEntry OBJECT-TYPE
	SYNTAX GnOduStatusEntry
	ACCESS  not-accessible
	STATUS mandatory
	DESCRIPTION
	"This is an entry in the ODU Status Table. This table
	contains two rows, indexed by ifIndex= 1 for local ODU and
	ifIndex = 101 for remote ODU."
	INDEX {  ifIndex }
	::= { gnOduStatusTable 1 }


GnOduStatusEntry ::=
	    SEQUENCE {
	gnOduStatusCelsiusTemp
	  INTEGER,
	gnOduStatusFahrenheitTemp
	  INTEGER,
	gnOduStatusTransmitLevel
	  INTEGER,
    	gnOduStatusReceiveLevel
      	   INTEGER,
	gnOduStatusSynthesizerVCOLock
	   OCTET STRING,
	gnOduStatusPowerSupply
	   OCTET STRING,
	gnOduStatusClearLoopTimer
		INTEGER
    }

gnOduStatusCelsiusTemp OBJECT-TYPE
	SYNTAX  INTEGER (-50..80)
	ACCESS  read-only
	STATUS mandatory
	DESCRIPTION
	"This is the temperature of the ODU in degrees Celsius."
	::= { gnOduStatusEntry 1 }

gnOduStatusFahrenheitTemp OBJECT-TYPE
	SYNTAX  INTEGER  (-58..176)
	ACCESS  read-only
	STATUS mandatory
	DESCRIPTION
	"This is the temperature of the ODU in degrees Fahrenheit."
	::= { gnOduStatusEntry 2 }

gnOduStatusTransmitLevel OBJECT-TYPE
	SYNTAX  INTEGER (-99..30)
	ACCESS  read-only
	STATUS mandatory
	DESCRIPTION
	"This is the transmit level of the signal transmitted by the radios
	 transmitter, displayed in DBM."
	::= { gnOduStatusEntry 3 }

gnOduStatusReceiveLevel OBJECT-TYPE
	SYNTAX  INTEGER (-99..-15)
	ACCESS  read-only
	STATUS mandatory
	DESCRIPTION
	"This is the receive level of the signal transmitted by the radios
	 transmitter, displayed in DBM."
	::= { gnOduStatusEntry 4}


gnOduStatusSynthesizerVCOLock OBJECT-TYPE
	SYNTAX  OCTET STRING(SIZE(1))
	ACCESS  read-only
	STATUS mandatory
	DESCRIPTION
	"This octet represents the ODU status as follows (bit 1, LSB):
	bit 1 on = TX IF synthesizer
	bit 2 on = RX IF synthesizer
	bit 3 on = Xband synthesizer
	bit 4 on = History TX IF synthesizer
	bit 5 on = History RX IF synthesizer
	bit 6 on = History Xband synthesizer  "
	::= { gnOduStatusEntry 5}

gnOduStatusPowerSupply OBJECT-TYPE
	SYNTAX OCTET STRING(SIZE(1))
	ACCESS  read-only
	STATUS mandatory
	DESCRIPTION
	"This octet represents the status of the power
	supplies of the ODU:
	bit 1 on = +5V faulty
	bit 2 on = +8V faulty
	bit 3 on = +12V faulty
        bit 4 on = -12V faulty."
	::= { gnOduStatusEntry 6}

gnOduStatusClearLoopTimer OBJECT-TYPE
	SYNTAX INTEGER (0..1440)
	ACCESS  read-only
	STATUS mandatory
	DESCRIPTION
	"This variable indicates the remaining time (in minutes) 
	till the relevant odu loopback timer will be expired.
	when starting a loopback and the value of gnGenCfgClearLoopTimeout is x,
	the gnOduStatusClearLoopTimer will be also x, after one minute it will be x-1, etc."
	::= { gnOduStatusEntry 7}


-- This part of the MIB deals with the performance monitoring
-- of the ODU part of the system.
gnOduMonitor  OBJECT IDENTIFIER ::= { gnODU 3 }
-- This part is built according the habits in the telcos/datacom community.
-- There are three tables:
-- gnOduMonCurrTable that keeps the counters of the current 15 min interval.
-- gnOduMonIntervalTable that keeps the counters of the past 96 intervals.
-- gnOduMonDayTable that keeps the counters of the past 30 days.

gnOduMonCurrTable OBJECT-TYPE
	SYNTAX  SEQUENCE OF GnOduMonCurrEntry
	ACCESS  not-accessible
	STATUS mandatory
	DESCRIPTION
	"This table defines/keeps the counters of the current 15 min interval."
	::= { gnOduMonitor 1 }

gnOduMonCurrEntry OBJECT-TYPE
	SYNTAX GnOduMonCurrEntry
	ACCESS  not-accessible
	STATUS mandatory
	DESCRIPTION
	"This is an entry in the Current Interval Table. This table
	contains two rows, indexed by ifIndex= 1 for local ODU and
	ifIndex = 101 for remote ODU."
	INDEX {  ifIndex }
	::= { gnOduMonCurrTable 1 }

GnOduMonCurrEntry ::=
	    SEQUENCE {
	gnOduMonCurrMinRL
	  INTEGER,
   	gnOduMonCurrMaxRL
	  INTEGER,
	gnOduMonCurrTLThresh1Exceed
	  Counter,
	gnOduMonCurrRLThresh1Exceed
	  Counter,
	gnOduMonCurrRLThresh2Exceed
	  Counter,
	gnOduMonCurrDayMinRL
	   INTEGER,
	gnOduMonCurrDayMaxRL
	   INTEGER,
	gnOduMonCurrDayTLThresh1Exceed
	  Counter,
	gnOduMonCurrDayRLThresh1Exceed
	  Counter,
	gnOduMonCurrDayRLThresh2Exceed
	  Counter,
	gnOduMonCurrMinTL
	  INTEGER,
   	gnOduMonCurrMaxTL
	  INTEGER,
	gnOduMonCurrDayMinTL
	  INTEGER,
   	gnOduMonCurrDayMaxTL
	  INTEGER
}


gnOduMonCurrMinRL OBJECT-TYPE
	SYNTAX  INTEGER
	ACCESS  read-only
	STATUS mandatory
	DESCRIPTION
	"The minimum received signal level (RL) in the current 15 minute interval. 
(in DBM) "
	::= { gnOduMonCurrEntry 1 }


gnOduMonCurrMaxRL OBJECT-TYPE
	SYNTAX  INTEGER
	ACCESS  read-only
	STATUS mandatory
	DESCRIPTION
	"The maximum received signal level (RL) in the current 15 minute interval. 
(in DBM). "
	::= { gnOduMonCurrEntry 2 }

gnOduMonCurrTLThresh1Exceed OBJECT-TYPE
	SYNTAX  Counter
	ACCESS  read-only
	STATUS mandatory
	DESCRIPTION
	" The number of seconds TL exceeded the TL1
	 threshold in the last 15 minutes."
	::= { gnOduMonCurrEntry 3 }


gnOduMonCurrRLThresh1Exceed OBJECT-TYPE
	SYNTAX  Counter
	ACCESS  read-only
	STATUS mandatory
	DESCRIPTION
	" The number of seconds RL exceeded the RL1
	 threshold in the last 15 minutes."
	::= { gnOduMonCurrEntry 4 }

gnOduMonCurrRLThresh2Exceed OBJECT-TYPE
	SYNTAX  Counter
	ACCESS  read-only
	STATUS mandatory
	DESCRIPTION
	" The number of seconds RL exceeded the RL2
	 threshold in the last 15 minutes."
	::= { gnOduMonCurrEntry 5 }


gnOduMonCurrDayMinRL OBJECT-TYPE
	SYNTAX  INTEGER
	ACCESS  read-only
	STATUS mandatory
	DESCRIPTION
	" The minimum Receive Level (in DBM).
	in the last 24 hours."
	::= { gnOduMonCurrEntry 6}


gnOduMonCurrDayMaxRL OBJECT-TYPE
	SYNTAX  INTEGER
	ACCESS  read-only
	STATUS mandatory
	DESCRIPTION
	" The maximum Receive Level (in DBM).
	in the last 24 hours."
	::= { gnOduMonCurrEntry 7}

gnOduMonCurrDayTLThresh1Exceed OBJECT-TYPE
	SYNTAX  Counter
	ACCESS  read-only
	STATUS mandatory
	DESCRIPTION
	" The number of seconds TL exceeded the TL1 threshold
	in the last 24 hours."
	::= { gnOduMonCurrEntry 8}


gnOduMonCurrDayRLThresh1Exceed OBJECT-TYPE
	SYNTAX  Counter
	ACCESS  read-only
	STATUS mandatory
	DESCRIPTION
	" The number of seconds RL exceeded the RL1 threshold
	in the last 24 hours."
	::= { gnOduMonCurrEntry 9 }

gnOduMonCurrDayRLThresh2Exceed OBJECT-TYPE
	SYNTAX  Counter
	ACCESS  read-only
	STATUS mandatory
	DESCRIPTION
	" The number of seconds RL exceeded the RL2 threshold
	in the last 24 hours."
	::= { gnOduMonCurrEntry 10 }

gnOduMonCurrMinTL OBJECT-TYPE
	SYNTAX  INTEGER
	ACCESS  read-only
	STATUS mandatory
	DESCRIPTION
	"The minimum transmitted signal level (TL) in the current 15 minute interval. 
(in DBM) "
	::= { gnOduMonCurrEntry 11 }


gnOduMonCurrMaxTL OBJECT-TYPE
	SYNTAX  INTEGER
	ACCESS  read-only
	STATUS mandatory
	DESCRIPTION
	"The maximum transmitted signal level (TL) in the current 15 minute interval. 
(in DBM). "
	::= { gnOduMonCurrEntry 12 }

gnOduMonCurrDayMinTL OBJECT-TYPE
	SYNTAX  INTEGER
	ACCESS  read-only
	STATUS mandatory
	DESCRIPTION
	" The minimum Transmitted Level (in DBM).
	in the last 24 hours."
	::= { gnOduMonCurrEntry 13}


gnOduMonCurrDayMaxTL OBJECT-TYPE
	SYNTAX  INTEGER
	ACCESS  read-only
	STATUS mandatory
	DESCRIPTION
	" The maximum Transmitted Level (in DBM).
	in the last 24 hours."
	::= { gnOduMonCurrEntry 14}



gnOduMonIntervalTable OBJECT-TYPE
	SYNTAX  SEQUENCE OF GnOduMonIntervalEntry
	ACCESS  not-accessible
	STATUS mandatory
	DESCRIPTION
	"This table defines/keeps the counters of the 96 last intervals of 15 min."
	::= { gnOduMonitor 2 }

gnOduMonIntervalEntry OBJECT-TYPE
	SYNTAX GnOduMonIntervalEntry
	ACCESS  not-accessible
	STATUS mandatory
	DESCRIPTION
	"This is an entry in the Interval Table. This table
	is indexed by ifIndex= 1 for local ODU and
	ifIndex = 101 for remote ODU and by interval idx"
	INDEX {  ifIndex, gnOduMonIntervalIdx }
	::= { gnOduMonIntervalTable 1 }

GnOduMonIntervalEntry ::=
	    SEQUENCE {
	gnOduMonIntervalIdx
	  INTEGER,
	gnOduMonIntervalMinRL
	  INTEGER,
   	gnOduMonIntervalMaxRL
	  INTEGER,
	gnOduMonIntervalTLThresh1Exceed
	  Counter,
    gnOduMonIntervalEvent
	   OCTET STRING,
	gnOduMonIntervalRLThresh1Exceed
	  Counter,
	gnOduMonIntervalRLThresh2Exceed
	  Counter,
	gnOduMonIntervalMinTL
	  INTEGER,
   	gnOduMonIntervalMaxTL
	  INTEGER
}

gnOduMonIntervalIdx OBJECT-TYPE
	SYNTAX  INTEGER (1..96)
	ACCESS  read-only
	STATUS mandatory
	DESCRIPTION
	" The interval number to which this row is related. "
	::= { gnOduMonIntervalEntry 1 }


gnOduMonIntervalMinRL OBJECT-TYPE
	SYNTAX  INTEGER
	ACCESS  read-only
	STATUS mandatory
	DESCRIPTION
	" The minimum RL in a 15 minutes interval. (in DBM). "
	::= { gnOduMonIntervalEntry 2 }

gnOduMonIntervalMaxRL OBJECT-TYPE
	SYNTAX  INTEGER
	ACCESS  read-only
	STATUS mandatory
	DESCRIPTION
	" The maximum RL in a 15 minutes interval. (in DBM). "
	::= { gnOduMonIntervalEntry 3 }

gnOduMonIntervalTLThresh1Exceed OBJECT-TYPE
	SYNTAX  Counter
	ACCESS  read-only
	STATUS mandatory
	DESCRIPTION
	" The number of seconds TL exceeded the TL1
	 threshold in a 15 minutes interval."
	::= { gnOduMonIntervalEntry 4 }


gnOduMonIntervalEvent OBJECT-TYPE
	SYNTAX  OCTET STRING (SIZE(1))
	ACCESS  read-only
	STATUS mandatory
	DESCRIPTION
	" Events
	 bit 1 = CommDisc.
	 bit 2 = CommCon
     bit 3 = ATPC2Max.
	 bit 4 = ATPC2Norm.
	 Included for future development, not currently supported."
	::= { gnOduMonIntervalEntry 5 }

gnOduMonIntervalRLThresh1Exceed OBJECT-TYPE
	SYNTAX  Counter
	ACCESS  read-only
	STATUS mandatory
	DESCRIPTION
	" The number of seconds RL exceeded the RL1
	 threshold in a 15 minutes interval."
	::= { gnOduMonIntervalEntry 6 }

gnOduMonIntervalRLThresh2Exceed OBJECT-TYPE
	SYNTAX  Counter
	ACCESS  read-only
	STATUS mandatory
	DESCRIPTION
	" The number of seconds RL exceeded the RL2
	 threshold in a 15 minutes interval."
	::= { gnOduMonIntervalEntry 7 }

gnOduMonIntervalMinTL OBJECT-TYPE
	SYNTAX  INTEGER
	ACCESS  read-only
	STATUS mandatory
	DESCRIPTION
	" The minimum TL in a 15 minutes interval. (in DBM). "
	::= { gnOduMonIntervalEntry 8 }

gnOduMonIntervalMaxTL OBJECT-TYPE
	SYNTAX  INTEGER
	ACCESS  read-only
	STATUS mandatory
	DESCRIPTION
	" The maximum TL in a 15 minutes interval. (in DBM). "
	::= { gnOduMonIntervalEntry 9 }



gnOduMonDayTable OBJECT-TYPE
	SYNTAX  SEQUENCE OF GnOduMonDayEntry
	ACCESS  not-accessible
	STATUS mandatory
	DESCRIPTION
	"This table defines/keeps the counters of 96 intervals of 15 min."
	::= { gnOduMonitor 3 }

gnOduMonDayEntry OBJECT-TYPE
	SYNTAX GnOduMonDayEntry
	ACCESS  not-accessible
	STATUS mandatory
	DESCRIPTION
	"This is an entry in the Days Table. This table
	is indexed by ifIndex= 1 for local ODU and
	ifIndex = 101 for remote ODU and by day idx.
	gnOduMonDayIdx = 1 is one day from now,
	gnOduMonDayIdx = 2 is two days from now, and so on..."
	INDEX {  ifIndex, gnOduMonDayIdx }
	::= { gnOduMonDayTable 1 }

GnOduMonDayEntry ::=
	    SEQUENCE {
	gnOduMonDayIdx
	  INTEGER,
	gnOduMonDayMinRL
	   INTEGER,
	gnOduMonDayMaxRL
	   INTEGER,
	gnOduMonDayTLThresh1Exceed
	  Counter,
	gnOduMonDayRLThresh1Exceed
	  Counter,
	gnOduMonDayRLThresh2Exceed
	  Counter,
	gnOduMonDayMinTL
	   INTEGER,
	gnOduMonDayMaxTL
	   INTEGER
}

gnOduMonDayIdx OBJECT-TYPE
	SYNTAX  INTEGER (1..30)
	ACCESS  read-only
	STATUS mandatory
	DESCRIPTION
	" The interval number to which this row is related. "
	::= { gnOduMonDayEntry 1 }


gnOduMonDayMinRL OBJECT-TYPE
	SYNTAX  INTEGER
	ACCESS  read-only
	STATUS mandatory
	DESCRIPTION
	" The minimum Receive Level (in DBM).
	in a 24 hour interval."
	::= { gnOduMonDayEntry 2}

gnOduMonDayMaxRL OBJECT-TYPE
	SYNTAX  INTEGER
	ACCESS  read-only
	STATUS mandatory
	DESCRIPTION
	" The maximum Receive Level (in DBM).
	in a 24 hour interval."
	::= { gnOduMonDayEntry 3}

gnOduMonDayTLThresh1Exceed OBJECT-TYPE
	SYNTAX  Counter
	ACCESS  read-only
	STATUS mandatory
	DESCRIPTION
	" The number of seconds TL exceeded the TL1 threshold
	in a 24 hour interval."
	::= { gnOduMonDayEntry 4}


gnOduMonDayRLThresh1Exceed OBJECT-TYPE
	SYNTAX  Counter
	ACCESS  read-only
	STATUS mandatory
	DESCRIPTION
	" The number of seconds RL exceeded the RL1 threshold
	in a 24 hour interval."
	::= { gnOduMonDayEntry 5}


gnOduMonDayRLThresh2Exceed OBJECT-TYPE
	SYNTAX  Counter
	ACCESS  read-only
	STATUS mandatory
	DESCRIPTION
	" The number of seconds RL exceeded the RL2 threshold
	in a 24 hour interval."
	::= { gnOduMonDayEntry 6}

gnOduMonDayMinTL OBJECT-TYPE
	SYNTAX  INTEGER
	ACCESS  read-only
	STATUS mandatory
	DESCRIPTION
	" The minimum Transmit Level (in DBM).
	in a 24 hour interval."
	::= { gnOduMonDayEntry 7}

gnOduMonDayMaxTL OBJECT-TYPE
	SYNTAX  INTEGER
	ACCESS  read-only
	STATUS mandatory
	DESCRIPTION
	" The maximum Transmit Level (in DBM).
	in a 24 hour interval."
	::= { gnOduMonDayEntry 8}



gnIDU OBJECT IDENTIFIER ::=  { gnUnits 2 }

gnMdm OBJECT IDENTIFIER ::=  { gnIDU 1 }

gnMdmStatTable OBJECT-TYPE
	SYNTAX  SEQUENCE OF GnMdmStatEntry
	ACCESS  not-accessible
	STATUS mandatory
	DESCRIPTION
	"This table maintains the status of the Indoor part
                of the system."
	::= { gnMdm 2 }

gnMdmStatEntry OBJECT-TYPE
	SYNTAX GnMdmStatEntry
	ACCESS  not-accessible
	STATUS mandatory
	DESCRIPTION
	"This is an entry in the IDU Modem Configuration Table. This table
	contains two rows, indexed by ifIndex= 1 for local modem and
	ifIndex = 101 for remote modem."
	INDEX {  ifIndex }
	::= { gnMdmStatTable 1 }


GnMdmStatEntry ::=
	    SEQUENCE {
	gnMdmModStatus
	  INTEGER,
	gnMdmDemodStatus
	  INTEGER,
	gnMdmDefectBlocks
	  INTEGER,
	gnMdmBytesCorrected
	  INTEGER,
	gnMdmClearBC
	  INTEGER
}



gnMdmModStatus OBJECT-TYPE
	SYNTAX  INTEGER  {
		ok(2),
		modulatorFault(3)
		}
	ACCESS  read-only
	STATUS mandatory
	DESCRIPTION
	"This parameters indicates a modem fault. "
	::= { gnMdmStatEntry 1 }

gnMdmDemodStatus OBJECT-TYPE
	SYNTAX  INTEGER
	ACCESS  read-only
	STATUS mandatory
	DESCRIPTION
	"This parameters indicates a demodem fault - For Ceragon internal use."

	::= { gnMdmStatEntry 2 }

gnMdmDefectBlocks OBJECT-TYPE
	SYNTAX  INTEGER
	ACCESS  read-only
	STATUS mandatory
	DESCRIPTION
	"The number of defected blocks that could not be corrected by the
         FEC "
	::= { gnMdmStatEntry 3 }

gnMdmBytesCorrected OBJECT-TYPE
	SYNTAX  INTEGER
	ACCESS  read-only
	STATUS mandatory
	DESCRIPTION
	" Number of bytes corrected by the FEC"
	::= { gnMdmStatEntry 4 }


gnMdmClearBC OBJECT-TYPE
	SYNTAX  INTEGER {
				noAction(2),
             	clear(3)
	}
	ACCESS  read-write
	STATUS mandatory
	DESCRIPTION
	" clears Defected Blocks, Defected Bytes and Blocks Corrected."
	::= { gnMdmStatEntry 5 }

-- This group contains the parameters concerning the SPI
gnSpi  OBJECT IDENTIFIER ::=  { gnIDU 2 }

gnSpiCfgTable OBJECT-TYPE
	SYNTAX  SEQUENCE OF GnSpiCfgEntry
	ACCESS  not-accessible
	STATUS mandatory
	DESCRIPTION
	"This table defines the configuration of the SPI part
                of the system."
	::= { gnSpi 1 }

gnSpiCfgEntry OBJECT-TYPE
	SYNTAX GnSpiCfgEntry
	ACCESS  not-accessible
	STATUS mandatory
	DESCRIPTION
	"This is an entry in the SPI Configuration Table. This table
	contains two  rows, indexed by ifIndex= 2 for local SPI and
	ifIndex = 102 for remote SPI."
	INDEX {  ifIndex }
	::= { gnSpiCfgTable 1 }

GnSpiCfgEntry ::=
	    SEQUENCE {
	gnSpiCfgConnector
	 INTEGER
}

gnSpiCfgConnector OBJECT-TYPE
	SYNTAX  INTEGER {
			nointerface(1),
			fiber(2),
			electrical(3),
			utp(4),
			stp(5)
	}
	ACCESS  read-only
	STATUS mandatory
	DESCRIPTION
	" The physical connector of the SPI - Used only in old regenerators "
	DEFVAL { fiber }
	::= { gnSpiCfgEntry 1 }



-- This group contains the parameters concerning the MUX
gnMux OBJECT IDENTIFIER ::=  { gnIDU 3 }

-- This table is for parameters configuration of the regenerator

gnRstCfgTable OBJECT-TYPE
	SYNTAX  SEQUENCE OF GnRstCfgEntry
	ACCESS  not-accessible
	STATUS mandatory
	DESCRIPTION
	"This table defines the configuration of the regenerator part
                of the MUX."
	::= { gnMux 1 }

gnRstCfgEntry OBJECT-TYPE
	SYNTAX GnRstCfgEntry
	ACCESS  not-accessible
	STATUS mandatory
	DESCRIPTION
	"This is an entry in the Regenerator part of the MUX Configuration Table.
	This table contains a row for every interface which type is SONET(39).
	for example  regenerator on local and remote sides will have four entries 
1,2 for local
	IDU and 101 and 102 for remote IDU."
	INDEX {  ifIndex }
	::= { gnRstCfgTable 1 }

GnRstCfgEntry ::=
	    SEQUENCE {
	gnRstCfgTransmittedJ0
	   DisplayString,
	gnRstCfgExpectedJ0
	   DisplayString,
	gnRstCfgTransparencyJ0
	    INTEGER,
	gnRstCfgRSTAISMode
	     INTEGER,
	gnRstCfgRstEXCThresh
	     INTEGER,
	gnRstCfgRstSDThresh
	     INTEGER,
	gnRstCfgTransparencyE1
	     INTEGER,
	gnRstCfgTransparencyF1
	     INTEGER,
	gnRstCfgTransparencyUnscrambled
	     INTEGER,
	gnRstCfgMngByteLocation
	     INTEGER,
	gnRstCfgE1waysideChannel
	     INTEGER,
	gnRstCfgTransparencyDCCR
	     INTEGER,
	gnRstCfgTransparencyB1Chan
	     INTEGER,
	gnRstCfgTestActivate
	     OCTET STRING,
	gnRstCfgLoopbackOption
		INTEGER
	}



gnRstCfgTransmittedJ0 OBJECT-TYPE
	SYNTAX  DisplayString (SIZE(0..15))
	ACCESS  read-write
	STATUS mandatory
	DESCRIPTION
	"This is the J0 string that would be sent. This string must be 15 
characters in length."
	DEFVAL {"  FIBEAIR1500  "}
	::= { gnRstCfgEntry 1 }

gnRstCfgExpectedJ0 OBJECT-TYPE
	SYNTAX  DisplayString (SIZE(0..15))
	ACCESS  read-write
	STATUS mandatory
	DESCRIPTION
	"This is the J0 string that is expected to be received. This string must be 
15 characters in length."
	DEFVAL {"  FIBEAIR1500  "}
	::= { gnRstCfgEntry 2 }

gnRstCfgTransparencyJ0 OBJECT-TYPE
	SYNTAX  INTEGER {
			active(2),
			passthrough(3),
			notActive(4)
	}
	ACCESS  read-write
	STATUS mandatory
	DESCRIPTION
	" Send the received J0 string transparently or send the Transmitted J0
             configured string."
	DEFVAL { passthrough }
	::= { gnRstCfgEntry 3 }

gnRstCfgRSTAISMode OBJECT-TYPE
	SYNTAX  INTEGER {
			sendAIS(2),
			doNotSendAIS(3)
	}
	ACCESS  read-write
	STATUS mandatory
	DESCRIPTION
	" In the case of a J0 mismatch error, send or don't send AIS."
	DEFVAL { doNotSendAIS }
	::= { gnRstCfgEntry 4 }

gnRstCfgRstEXCThresh OBJECT-TYPE
	SYNTAX  INTEGER {
			tenExpMinus3(2),
			tenExpMinus4(3),
			tenExpMinus5(4)
	}
	ACCESS  read-write
	STATUS mandatory
	DESCRIPTION
	" If the bit error rate is higher than this threshold
	 an EXC alarm would be generated.
	EXC is for excessive."
	DEFVAL { tenExpMinus3}
	::= { gnRstCfgEntry 5 }

gnRstCfgRstSDThresh OBJECT-TYPE
	SYNTAX  INTEGER {
			tenExpMinus6(3),
			tenExpMinus7(4),
			tenExpMinus8(5),
			tenExpMinus9(6)
	}
	ACCESS  read-write
	STATUS mandatory
	DESCRIPTION
	" If the bit error rate is higher than this threshold
	 a SD alarm would be generated.
	SD is for Signal Degrade."
	DEFVAL { tenExpMinus6}
	::= { gnRstCfgEntry 6 }

gnRstCfgTransparencyE1 OBJECT-TYPE
	SYNTAX  INTEGER {
			active(2),
			passthrough(3),
			disable(4)
	}
	ACCESS  read-write
	STATUS mandatory
	DESCRIPTION
	"Transmit the order wire data received or terminate the E1 data received."
	DEFVAL { active }
	::= { gnRstCfgEntry 7 }

gnRstCfgTransparencyF1 OBJECT-TYPE
	SYNTAX  INTEGER {
			active(2),
			passthrough(3),
			disable(4)
	}
	ACCESS  read-write
	STATUS mandatory
	DESCRIPTION
	"Transmit the F1/User channel data received or terminate the F1/User channel data received.
	set the TransparencyF1 to disable when the User channel used by In-Band management."
	DEFVAL { active }
	::= { gnRstCfgEntry 8 }

gnRstCfgTransparencyUnscrambled OBJECT-TYPE
	SYNTAX  INTEGER {
			active(2),
			passthrough(3)
	}
	ACCESS  read-write
	STATUS mandatory
	DESCRIPTION
	"Transmit the unscrambled national bytes data received or terminate the 
unscrambled national bytes data received."
	DEFVAL { passthrough }
	::= { gnRstCfgEntry 9 }

gnRstCfgMngByteLocation OBJECT-TYPE
	SYNTAX  INTEGER {
			mediaSpecificBytes(2),
			spareA1A0Bytes(3),
			e1Byets(4),
			noMngBytes(5),
			dccr(6),
			dccm(7),
			userChannel(8),
			waysideChannel(9)
	}
	ACCESS  read-write
	STATUS mandatory
	DESCRIPTION
	"This parameter indicates which media specific bytes are in use and which 
are transparent.
	 not currently supported"
	DEFVAL { mediaSpecificBytes }
	::= { gnRstCfgEntry 10 }

gnRstCfgE1waysideChannel OBJECT-TYPE
	SYNTAX  INTEGER {
			enabled(2),
			disabled(3)
--			inband(4)
	}
	ACCESS  read-write
	STATUS mandatory
	DESCRIPTION
	"If this parameter is enabled, an E1 wayside channel will be sent
	through the network using the unused bytes in the SDH header."
	DEFVAL { enabled }
	::= { gnRstCfgEntry 11 }

gnRstCfgTransparencyDCCR OBJECT-TYPE
	SYNTAX  INTEGER {
			active(2),
			passthrough(3)
	}
	ACCESS  read-write
	STATUS mandatory
	DESCRIPTION
	"Transmit on the DCCR channel or terminate the DCCR channel."
	DEFVAL { passthrough }
	::= { gnRstCfgEntry 12 }

gnRstCfgTransparencyB1Chan OBJECT-TYPE
	SYNTAX  INTEGER {
			active(2),
			passthrough(3)
	}
	ACCESS  read-write
	STATUS mandatory
	DESCRIPTION
	"Correct B1 byte or send transmit it transparently ."
	DEFVAL { passthrough }
	::= { gnRstCfgEntry 13 }

gnRstCfgTestActivate OBJECT-TYPE
	SYNTAX  OCTET STRING (SIZE(1))
	ACCESS  read-write
	STATUS mandatory
	DESCRIPTION
	"This field allows the NMS to activate the
	following tests:
	bit 1 = 1 Force AIS
	bit 2 = 1 Force RDI."
	::= { gnRstCfgEntry 14 }

gnRstCfgLoopbackOption OBJECT-TYPE
	SYNTAX  INTEGER {
		noloopback(2),
		interfaceInterLoop(3),
		interfaceExterLoop(4)
		}
	ACCESS  read-write
	STATUS mandatory
	DESCRIPTION
	" This parameter enable the user to activate a loopback ."
	DEFVAL { noloopback }
	::= { gnRstCfgEntry  15 }

gnRstStatTable OBJECT-TYPE
	SYNTAX  SEQUENCE OF GnRstStatEntry
	ACCESS  not-accessible
	STATUS mandatory
	DESCRIPTION
	"This table defines the status of the regenerator part
                of the MUX."
	::= { gnMux 2 }

gnRstStatEntry OBJECT-TYPE
	SYNTAX GnRstStatEntry
	ACCESS  not-accessible
	STATUS mandatory
	DESCRIPTION
	"This is an entry in the Regenerator part of the MUX
	 Status Table. This table contains a row for every interface which type is SONET(39)."
	INDEX { ifIndex }
	::= { gnRstStatTable 1 }

GnRstStatEntry ::=
	    SEQUENCE {
	gnRstStatReceivedJ0
	     DisplayString,
	gnRstStatBERCur
	     INTEGER,
	gnRstStatStatus
	   OCTET STRING,
	gnRstStatClearLoopTimer
	     INTEGER

}

gnRstStatReceivedJ0 OBJECT-TYPE
	SYNTAX  DisplayString (SIZE(0..15))
	ACCESS  read-only
	STATUS mandatory
	DESCRIPTION
	"This is the J0 string received."
	::= { gnRstStatEntry 1 }

gnRstStatBERCur OBJECT-TYPE
	SYNTAX  INTEGER {
			tenExpMinus3(2),
			tenExpMinus4(3),
			tenExpMinus5(4),
			tenExpMinus6(5),
			tenExpMinus7(6),
			tenExpMinus8(7),
			tenExpMinus9(8),
			tenExpMinus10(9),
			tenExpMinus11(10),
			tenExpMinus12(11),
			tenExpMinus13(12),
			tenExpMinus14(13)
	}
	ACCESS  read-only
	STATUS mandatory
	DESCRIPTION
	" Current Bit Error Rate. "
	::= { gnRstStatEntry 2 }

gnRstStatStatus OBJECT-TYPE					   
	SYNTAX OCTET STRING(SIZE(2))				   
	ACCESS  read-only							   
	STATUS mandatory							   
	DESCRIPTION									   
	" bit 2  = LOS
	  bit 3  = LOF	
	  bit 7  = TIM
	  bit 9  = SD
	  bit 10 = EXC 
	  bit 11 = UNEXP"
	::= { gnRstStatEntry 3 }
	
gnRstStatClearLoopTimer OBJECT-TYPE
	SYNTAX INTEGER (0..1440)
	ACCESS  read-only
	STATUS mandatory
	DESCRIPTION
	"This variable indicates the remaining time (in minutes) 
	till the relevant loopback timer will be expired.
	when starting a loopback and the value of gnGenCfgClearLoopTimeout is x,
	the gnRstStatClearLoopTimer will be also x, after one minute it will be x-1, etc.
	gnRstStatClearLoopTimer.1 is for the radio aggregate loopbacks,
	gnRstStatClearLoopTimer.2 is for the line aggregate loopbacks"
	::= { gnRstStatEntry 4 }


-- Statistics For Regenerator
gnRstMon OBJECT IDENTIFIER ::=  { gnMux 3 }

gnRstMonCurrTable OBJECT-TYPE
	SYNTAX  SEQUENCE OF GnRstMonCurrEntry
	ACCESS  not-accessible
	STATUS mandatory
	DESCRIPTION
	"This table maintains the counters of the regenerator part
                of the MUX."
	::= { gnRstMon 1 }

gnRstMonCurrEntry OBJECT-TYPE
	SYNTAX GnRstMonCurrEntry
	ACCESS  not-accessible
	STATUS mandatory
	DESCRIPTION
	"This is an entry in the Regenerator part of the MUX
	 Counters Table. This table contains a row for every interface which type 
is SONET(39)."
	INDEX {  ifIndex }
	::= { gnRstMonCurrTable 1 }

GnRstMonCurrEntry ::=
	    SEQUENCE {
	--gnRstMonCurrES rfc1595
	--     Counter,
	--gnRstMonCurrSES
	--     Counter,
	gnRstMonCurrBBE
	     Gauge,
	gnRstMonCurrUAS
	     Gauge,
	--gnRstMonCurrOFS
	--     Counter,
	gnRstMonCurrLastDayES
	     Gauge,
	gnRstMonCurrLastDaySES
	     Gauge,
	gnRstMonCurrLastDayBBE
	     Gauge,
	gnRstMonCurrLastDayUAS
	     Gauge,
	gnRstMonCurrLastDayOFS
	     Gauge,
	gnRstMonCurrLastDayIDF
		 INTEGER
}



gnRstMonCurrBBE OBJECT-TYPE
	SYNTAX  Gauge
	ACCESS  read-only
	STATUS mandatory
	DESCRIPTION
	" The current number of Background Block Errors
	 starting from the present 15 minutes period."
	::= { gnRstMonCurrEntry 1}

gnRstMonCurrUAS OBJECT-TYPE
	SYNTAX  Gauge
	ACCESS  read-only
	STATUS mandatory
	DESCRIPTION
	" The current number of Unavailable Seconds
	 starting from the present 15 minutes period."
	::= { gnRstMonCurrEntry 2}


gnRstMonCurrLastDayES OBJECT-TYPE
	SYNTAX  Gauge
	ACCESS  read-only
	STATUS mandatory
	DESCRIPTION
	" The current number of Errored Seconds
	 starting from the present 24 hours period."
	::= { gnRstMonCurrEntry 3 }

gnRstMonCurrLastDaySES OBJECT-TYPE
	SYNTAX  Gauge
	ACCESS  read-only
	STATUS mandatory
	DESCRIPTION
	" The current number of Severely Errored Seconds
	 starting from the present 24 hours period."
	::= { gnRstMonCurrEntry 4 }

gnRstMonCurrLastDayBBE OBJECT-TYPE
	SYNTAX  Gauge
	ACCESS  read-only
	STATUS mandatory
	DESCRIPTION
	" The current number of Background Block Errors
	 starting from the present 24 hours period."
	::= { gnRstMonCurrEntry 5 }

gnRstMonCurrLastDayUAS OBJECT-TYPE
	SYNTAX  Gauge
	ACCESS  read-only
	STATUS mandatory
	DESCRIPTION
	" The current number of Unavailable Seconds
	 starting from the present 24 hours period."
	::= { gnRstMonCurrEntry 6 }

gnRstMonCurrLastDayOFS OBJECT-TYPE
	SYNTAX  Gauge
	ACCESS  read-only
	STATUS mandatory
	DESCRIPTION
	" The current number of Out Of Frame Seconds
	 starting from the present 24 hours period."
	::= { gnRstMonCurrEntry 7}

gnRstMonCurrLastDayIDF OBJECT-TYPE
	SYNTAX  INTEGER {
			off(2),
			on(3)
	}
	ACCESS read-only
	STATUS mandatory
	DESCRIPTION
	"IDF = Invalid Data Flag."
	DEFVAL { off }
	::= { gnRstMonCurrEntry 8 }


gnRstMonIntervalTable OBJECT-TYPE
	SYNTAX  SEQUENCE OF GnRstMonIntervalEntry
	ACCESS  not-accessible
	STATUS mandatory
	DESCRIPTION
	"This table maintains the counters of the regenerator part
                of the MUX per interval."
	::= { gnRstMon 2 }

gnRstMonIntervalEntry OBJECT-TYPE
	SYNTAX GnRstMonIntervalEntry
	ACCESS  not-accessible
	STATUS mandatory
	DESCRIPTION
	"This is an entry in the Regenerator part of the MUX
	 Counters Table. This table contains an interface index for every interface
	 which type is SONET(39).
	This table is indexed by an interval index, between 1
	to 96 and representing each one 15 minutes.
               The oldest is 96."
	INDEX {  ifIndex, gnRstMonIntervalIdx}
	::= { gnRstMonIntervalTable 1 }

GnRstMonIntervalEntry ::=
	    SEQUENCE {
	gnRstMonIntervalIdx
	      INTEGER,
	--gnRstMonIntervalES
	--     Counter,
	--gnRstMonIntervalSES
	--     Counter,
	gnRstMonIntervalBBE
	     Gauge,
	gnRstMonIntervalUAS
	--     Counter,
	--gnRstMonIntervalOFS
	     Gauge,
	gnRstMonIntervalIDF
		 INTEGER
--	     ,
--	gnRstMonIntervalTimeStampMonth				  
--	      INTEGER,					  
--	gnRstMonIntervalTimeStampDay				  
--	      INTEGER,					   
--	gnRstMonIntervalTimeStampHour
--	      INTEGER,
--	gnRstMonIntervalTimeStampMinute
--	      INTEGER
}

gnRstMonIntervalIdx OBJECT-TYPE
	SYNTAX INTEGER (1..96)
	ACCESS read-only
	STATUS mandatory
	DESCRIPTION
	"This table is indexed per interval number. Each interval
	is of 15 minutes and the oldest is 96."
	::= { gnRstMonIntervalEntry 1 }

gnRstMonIntervalBBE OBJECT-TYPE
	SYNTAX  Gauge
	ACCESS  read-only
	STATUS mandatory
	DESCRIPTION
	" The number of Background Block Errors
	per interval."
	::= { gnRstMonIntervalEntry 2}

gnRstMonIntervalUAS OBJECT-TYPE
	SYNTAX  Gauge
	ACCESS  read-only
	STATUS mandatory
	DESCRIPTION
	" The number of Unavailable Seconds per interval."
	::= { gnRstMonIntervalEntry 3}

gnRstMonIntervalIDF OBJECT-TYPE
	SYNTAX  INTEGER {
			off(2),
			on(3)
	}
	ACCESS read-only
	STATUS mandatory
	DESCRIPTION
	"IDF = Invalid Data Flag."
	DEFVAL { off }
	::= { gnRstMonIntervalEntry 4 }


-- gnRstMonIntervalTimeStampMonth OBJECT-TYPE
--	SYNTAX INTEGER (1..12)
--	ACCESS read-only
--	STATUS mandatory
--	DESCRIPTION
--	"The Month of this interval time stamp.Not currently supported."
--	::= { gnRstMonIntervalEntry 4 }

-- gnRstMonIntervalTimeStampDay OBJECT-TYPE
--		SYNTAX INTEGER (1..31)
--		ACCESS read-only
--		STATUS mandatory
--		DESCRIPTION
--		"The Day of this interval time stamp.Not currently supported."
--		::= { gnRstMonIntervalEntry 5 }

-- gnRstMonIntervalTimeStampHour OBJECT-TYPE
--		SYNTAX INTEGER (0..23)
--		ACCESS read-only
--		STATUS mandatory
--		DESCRIPTION
--		"The Hour of this interval time stamp.Not currently supported."
--		::= { gnRstMonIntervalEntry 6 }

-- gnRstMonIntervalTimeStampMinute OBJECT-TYPE
--		SYNTAX INTEGER (0..59)
--		ACCESS read-only
--		STATUS mandatory
--		DESCRIPTION
--		"The Minute of this interval time stamp.Not currently supported."
--		::= { gnRstMonIntervalEntry 7 }


gnRstMonDayTable OBJECT-TYPE
	SYNTAX  SEQUENCE OF GnRstMonDayEntry
	ACCESS  not-accessible
	STATUS mandatory
	DESCRIPTION
	"This table maintains the counters of the regenerator part
                of the MUX per 24 hours interval."
	::= { gnRstMon 3 }

gnRstMonDayEntry OBJECT-TYPE
	SYNTAX GnRstMonDayEntry
	ACCESS  not-accessible
	STATUS mandatory
	DESCRIPTION
	"This is an entry in the Regenerator part of the MUX
	 Counters Table. This table contains an interface index for every interface
	 which type is SONET(39).
	This table is indexed by an interval index, between 1
	to 30 and representing each one 24 hours.
               The oldest is 30."
	INDEX {  ifIndex, gnRstMonDayIdx}
	::= { gnRstMonDayTable 1 }

GnRstMonDayEntry ::=
	    SEQUENCE {
	gnRstMonDayIdx
	      INTEGER,
	gnRstMonDayES
	     Gauge,
	gnRstMonDaySES
	     Gauge,
	gnRstMonDayBBE
	     Gauge,
	gnRstMonDayUAS
	     Gauge,
	gnRstMonDayOFS
	     Gauge, 
	gnRstMonDayIDF
		 INTEGER

--	,
-- 	gnRstMonDayTimeStampMonth
--		      INTEGER,
--		gnRstMonDayTimeStampDay
--		      INTEGER,
--		gnRstMonDayTimeStampHour
--		      INTEGER,
--		gnRstMonDayTimeStampMinute
--		      INTEGER
}

gnRstMonDayIdx OBJECT-TYPE
	SYNTAX INTEGER (1..30)
	ACCESS read-only
	STATUS mandatory
	DESCRIPTION
	"This table is indexed per interval number. Each interval
	is of 24 hours and the oldest is 30."
	::= { gnRstMonDayEntry 1 }

gnRstMonDayES OBJECT-TYPE
	SYNTAX  Gauge
	ACCESS  read-only
	STATUS mandatory
	DESCRIPTION
	" The number of Errored Seconds per interval of 24 hours."
	::= { gnRstMonDayEntry 2}

gnRstMonDaySES OBJECT-TYPE
	SYNTAX  Gauge
	ACCESS  read-only
	STATUS mandatory
	DESCRIPTION
	" The number of Severely Errored Seconds
	 per interval of 24 hours."
	::= { gnRstMonDayEntry 3}

gnRstMonDayBBE OBJECT-TYPE
	SYNTAX  Gauge
	ACCESS  read-only
	STATUS mandatory
	DESCRIPTION
	" The number of Background Block Errors
	 per interval of 24 hours."
	::= { gnRstMonDayEntry 4 }

gnRstMonDayUAS OBJECT-TYPE
	SYNTAX  Gauge
	ACCESS  read-only
	STATUS mandatory
	DESCRIPTION
	" The number of Unavailable Seconds
	 per interval of 24 hours."
	::= { gnRstMonDayEntry 5 }

gnRstMonDayOFS OBJECT-TYPE
	SYNTAX  Gauge
	ACCESS  read-only
	STATUS mandatory
	DESCRIPTION
	" The number of Out Of Frame Seconds
	 per interval of 24 hours."
	::= { gnRstMonDayEntry 6}

gnRstMonDayIDF OBJECT-TYPE
	SYNTAX  INTEGER {
			off(2),
			on(3)
	}
	ACCESS read-only
	STATUS mandatory
	DESCRIPTION
	"IDF = Invalid Data Flag."
	DEFVAL { off }
	::= { gnRstMonDayEntry 7 }


-- gnRstMonDayTimeStampMonth OBJECT-TYPE
--		SYNTAX INTEGER (1..12)
--		ACCESS read-only
--		STATUS mandatory
--		DESCRIPTION
--		"The Month of this interval time stamp.Not currently supported."
--		::= { gnRstMonDayEntry 7 }

-- gnRstMonDayTimeStampDay OBJECT-TYPE
--		SYNTAX INTEGER (1..31)
--		ACCESS read-only
--		STATUS mandatory
--		DESCRIPTION
--		"The Day of this interval time stamp.Not currently supported."
--		::= { gnRstMonDayEntry 8 }

-- gnRstMonDayTimeStampHour OBJECT-TYPE
--		SYNTAX INTEGER (0..23)
--		ACCESS read-only
--		STATUS mandatory
--		DESCRIPTION
--		"The Hour of this interval time stamp.Not currently supported."
--		::= { gnRstMonDayEntry 9 }

-- gnRstMonDayTimeStampMinute OBJECT-TYPE
--		SYNTAX INTEGER (0..59)
--		ACCESS read-only
--		STATUS mandatory
--		DESCRIPTION
--		"The Minute of this interval time stamp.Not currently supported."
--		::= { gnRstMonDayEntry 10 }



-- MST part of the MUX. All of the MST tables are included for future 
-- development and are not currently implemented.
gnMstCfgTable OBJECT-TYPE
	SYNTAX  SEQUENCE OF GnMstCfgEntry
	ACCESS  not-accessible
	STATUS mandatory
	DESCRIPTION
	"This table maintains the counters of the MST part
                of the MUX."
	::= { gnMux 4 }

gnMstCfgEntry OBJECT-TYPE
	SYNTAX GnMstCfgEntry
	ACCESS  not-accessible
	STATUS mandatory
	DESCRIPTION
	"This is an entry in the MST part of the MUX
	 Configuration Table. This table contains a row for every interface
	 which type is SONET(39)."
	INDEX {  ifIndex }
	::= { gnMstCfgTable 1 }

GnMstCfgEntry ::=
	    SEQUENCE {
	gnMstCfgEXCThresh
		INTEGER,
	gnMstCfgSDThresh
	   INTEGER
}


gnMstCfgEXCThresh OBJECT-TYPE
	SYNTAX  INTEGER {
			tenExpMinus3(2),
			tenExpMinus4(3),
			tenExpMinus5(4)
	}
	ACCESS  read-write
	STATUS mandatory
	DESCRIPTION
	" If the bit error rate is higher than this threshold
	 an EXC alarm would be generated.
	EXC is for excessive."
	DEFVAL { tenExpMinus3}
	::= { gnMstCfgEntry 1 }

gnMstCfgSDThresh OBJECT-TYPE
	SYNTAX  INTEGER {
			tenExpMinus6(3),
			tenExpMinus7(4),
			tenExpMinus8(5),
			tenExpMinus9(6)
	}
	ACCESS  read-write
	STATUS mandatory
	DESCRIPTION
	" If the bit error rate is higher than this threshold
	 a SD alarm would be generated.
	SD is for Signal Degrade."
	DEFVAL { tenExpMinus6}
	::= { gnMstCfgEntry 2 }


gnMstStatTable OBJECT-TYPE
	SYNTAX  SEQUENCE OF GnMstStatEntry
	ACCESS  not-accessible
	STATUS mandatory
	DESCRIPTION
	"This table defines the status of the MST part
                of the MUX."
	::= { gnMux 5 }

gnMstStatEntry OBJECT-TYPE
	SYNTAX GnMstStatEntry
	ACCESS  not-accessible
	STATUS mandatory
	DESCRIPTION
	"This is an entry in the MST part of the MUX
	 Status Table. This table contains a row for every interface which type is 
SONET(39)."
	INDEX {  ifIndex }
	::= { gnMstStatTable 1 }

GnMstStatEntry ::=
	    SEQUENCE {
	gnMstStatReceivedS1
	     INTEGER,
	gnMstStatStatus
	     OCTET STRING,
	gnMstStatTransmitS1
		INTEGER,
	gnMstStatCurrentBer
		INTEGER,
	gnMstStatReceivedK1
	     INTEGER,
	gnMstStatReceivedK2
	     INTEGER,
	gnMstStatTransmitK1
		INTEGER,
	gnMstStatTransmitK2
		INTEGER
}

gnMstStatReceivedS1 OBJECT-TYPE
	SYNTAX  INTEGER (0..15)
	ACCESS  read-only
	STATUS mandatory
	DESCRIPTION
	" Received Synchronization status byte."
	::= { gnMstStatEntry 1 }

gnMstStatStatus OBJECT-TYPE
	SYNTAX OCTET STRING(SIZE(4))
	ACCESS  read-only
	STATUS mandatory
	DESCRIPTION
	" Alarm status. Bit 1 is MSB, bit=1 when alarm active.
	bit 5  = RDI
	bit 6  = AIS
	bit 9  = SD
	bit 10 = EXC
	bit 16 = PAM (MSP)
	bit 17 = SCM (MSP)
	bit 18 = INV (MSP)
	"
	::= { gnMstStatEntry 2 }

gnMstStatTransmitS1 OBJECT-TYPE
	SYNTAX  INTEGER (0..15)
	ACCESS  read-only
	STATUS mandatory
	DESCRIPTION
	" Transmitted Synchronization status byte."
	::= { gnMstStatEntry 3 }

gnMstStatCurrentBer OBJECT-TYPE
	SYNTAX  INTEGER {
			tenExpMinus3(2),
			tenExpMinus4(3),
			tenExpMinus5(4),
			tenExpMinus6(5),
			tenExpMinus7(6),
			tenExpMinus8(7),
			tenExpMinus9(8),
			tenExpMinus10(9),
			tenExpMinus11(10),
			tenExpMinus12(11),
			tenExpMinus13(12),
			tenExpMinus14(13)
	}
	ACCESS  read-only
	STATUS mandatory
	DESCRIPTION
	" "
	::= { gnMstStatEntry 4 }

gnMstStatReceivedK1 OBJECT-TYPE
	SYNTAX  INTEGER (0..255)
	ACCESS  read-only
	STATUS mandatory
	DESCRIPTION
	"Received K1 byte (Automatic Protection Switch message)."
	::= { gnMstStatEntry 5 }

gnMstStatReceivedK2 OBJECT-TYPE
	SYNTAX  INTEGER (0..255)
	ACCESS  read-only
	STATUS mandatory
	DESCRIPTION
	"Received K2 byte (Automatic Protection Switch message)."
	::= { gnMstStatEntry 6 }

gnMstStatTransmitK1 OBJECT-TYPE
	SYNTAX  INTEGER (0..255)
	ACCESS  read-only
	STATUS mandatory
	DESCRIPTION
	"Transmitted K1 byte (Automatic Protection Switch message)."
	::= { gnMstStatEntry 7 }

gnMstStatTransmitK2 OBJECT-TYPE
	SYNTAX  INTEGER (0..255)
	ACCESS  read-only
	STATUS mandatory
	DESCRIPTION
	"Transmitted K2 byte (Automatic Protection Switch message)."
	::= { gnMstStatEntry 8 }


-- Statistics For MST. All MST tables are included for future development 
-- and are not currently implemented.
gnMstMon OBJECT IDENTIFIER ::=  { gnMux 6 }
gnMstMonCurrTable OBJECT-TYPE
	SYNTAX  SEQUENCE OF GnMstMonCurrEntry
	ACCESS  not-accessible
	STATUS mandatory
	DESCRIPTION
	"This table maintains the counters of the MST part
                of the MUX."
	::= { gnMstMon 1 }

gnMstMonCurrEntry OBJECT-TYPE
	SYNTAX GnMstMonCurrEntry
	ACCESS  not-accessible
	STATUS mandatory
	DESCRIPTION
	"This is an entry in the MST part of the MUX
	 Counters Table. This table contains a row for every interface which type 
is SONET(39)."
	INDEX {  ifIndex }
	::= { gnMstMonCurrTable 1 }

GnMstMonCurrEntry ::=
	    SEQUENCE {
	--gnMstMonCurrES rfc1595
	--     Counter,
	--gnMstMonCurrSES
	--     Counter,
	gnMstMonCurrBBE
	     Gauge,
	gnMstMonCurrUAS
	     Gauge,
	gnMstMonCurrLastDayES
	     Gauge,
	gnMstMonCurrLastDaySES
	     Gauge,
	gnMstMonCurrLastDayBBE
	     Gauge,
	gnMstMonCurrLastDayUAS
	     Gauge
}



gnMstMonCurrBBE OBJECT-TYPE
	SYNTAX  Gauge
	ACCESS  read-only
	STATUS mandatory
	DESCRIPTION
	" The current number of Background Block Errors
	 starting  from the present 15 minutes period."
	::= { gnMstMonCurrEntry 1}

gnMstMonCurrUAS OBJECT-TYPE
	SYNTAX  Gauge
	ACCESS  read-only
	STATUS mandatory
	DESCRIPTION
	" The current number of Unavailable Seconds
	 starting from the present 15 minutes period."
	::= { gnMstMonCurrEntry 2}


gnMstMonCurrLastDayES OBJECT-TYPE
	SYNTAX  Gauge
	ACCESS  read-only
	STATUS mandatory
	DESCRIPTION
	" The current number of Errored Seconds
	 starting from the present 24 hours period."
	::= { gnMstMonCurrEntry 3 }

gnMstMonCurrLastDaySES OBJECT-TYPE
	SYNTAX  Gauge
	ACCESS  read-only
	STATUS mandatory
	DESCRIPTION
	" The current number of Severely Errored Seconds
	 starting from the present 24 hours period."
	::= { gnMstMonCurrEntry 4 }

gnMstMonCurrLastDayBBE OBJECT-TYPE
	SYNTAX  Gauge
	ACCESS  read-only
	STATUS mandatory
	DESCRIPTION
	" The current number of Background Block Errors
	 starting from the present 24 hours period."
	::= { gnMstMonCurrEntry 5 }

gnMstMonCurrLastDayUAS OBJECT-TYPE
	SYNTAX  Gauge
	ACCESS  read-only
	STATUS mandatory
	DESCRIPTION
	" The current number of Unavailable Seconds
	 starting from the present 24 hours period."
	::= { gnMstMonCurrEntry 6 }


gnMstMonIntervalTable OBJECT-TYPE
	SYNTAX  SEQUENCE OF GnMstMonIntervalEntry
	ACCESS  not-accessible
	STATUS mandatory
	DESCRIPTION
	"This table maintains the counters of the MST part
                of the MUX per interval."
	::= { gnMstMon 2 }

gnMstMonIntervalEntry OBJECT-TYPE
	SYNTAX GnMstMonIntervalEntry
	ACCESS  not-accessible
	STATUS mandatory
	DESCRIPTION
	"This is an entry in the MST part of the MUX
	 Counters Table. This table contains an interface index for every interface
	 which type is SONET(39).
	This table is indexed by an interval index, between 1
	to 96 and representing each one 15 minutes.
               The oldest is 96."
	INDEX {  ifIndex, gnMstMonIntervalIdx}
	::= { gnMstMonIntervalTable 1 }

GnMstMonIntervalEntry ::=
	    SEQUENCE {
	gnMstMonIntervalIdx
	      INTEGER,
	--gnMstMonIntervalES
	--     Counter,
	--gnMstMonIntervalSES
	--     Counter,
	gnMstMonIntervalBBE
	     Gauge,
	gnMstMonIntervalUAS
	     Gauge
}

gnMstMonIntervalIdx OBJECT-TYPE
	SYNTAX INTEGER (1..96)
	ACCESS read-only
	STATUS mandatory
	DESCRIPTION
	"This table is indexed per interval number. Each interval
	is of 15 minutes and the oldest is 96."
	::= { gnMstMonIntervalEntry 1 }

gnMstMonIntervalBBE OBJECT-TYPE
	SYNTAX  Gauge
	ACCESS  read-only
	STATUS mandatory
	DESCRIPTION
	" The number of Background Block Errors
	per interval."
	::= { gnMstMonIntervalEntry 2}

gnMstMonIntervalUAS OBJECT-TYPE
	SYNTAX  Gauge
	ACCESS  read-only
	STATUS mandatory
	DESCRIPTION
	" The  number of Unavailable Seconds per interval."
	::= { gnMstMonIntervalEntry 3}


gnMstMonDayTable OBJECT-TYPE
	SYNTAX  SEQUENCE OF GnMstMonDayEntry
	ACCESS  not-accessible
	STATUS mandatory
	DESCRIPTION
	"This table maintains the counters of the MST part
                of the MUX per 24 hours interval."
	::= { gnMstMon 3 }

gnMstMonDayEntry OBJECT-TYPE
	SYNTAX GnMstMonDayEntry
	ACCESS  not-accessible
	STATUS mandatory
	DESCRIPTION
	"This is an entry in the MST part of the MUX
	 Counters Table. This table contains an interface index for every interface
	 which type is SONET(39).
	This table is indexed by an interval index, between 1
	to 30 and representing each one 24 hours.
               The oldest is 30."
	INDEX {  ifIndex, gnMstMonDayIdx}
	::= { gnMstMonDayTable 1 }

GnMstMonDayEntry ::=
	    SEQUENCE {
	gnMstMonDayIdx
	      INTEGER,
	gnMstMonDayES
	     Gauge,
	gnMstMonDaySES
	     Gauge,
	gnMstMonDayBBE
	     Gauge,
	gnMstMonDayUAS
	     Gauge
}

gnMstMonDayIdx OBJECT-TYPE
	SYNTAX INTEGER (1..30)
	ACCESS read-only
	STATUS mandatory
	DESCRIPTION
	"This table is indexed per interval number. Each interval
	is of 24 hours and the oldest is 30."
	::= { gnMstMonDayEntry 1 }

gnMstMonDayES OBJECT-TYPE
	SYNTAX  Gauge
	ACCESS  read-only
	STATUS mandatory
	DESCRIPTION
	" The number of Errored Seconds per interval of 24 hours."
	::= { gnMstMonDayEntry 2}

gnMstMonDaySES OBJECT-TYPE
	SYNTAX  Gauge
	ACCESS  read-only
	STATUS mandatory
	DESCRIPTION
	" The number of Severely Errored Seconds
	 per interval of 24 hours."
	::= { gnMstMonDayEntry 3}

gnMstMonDayBBE OBJECT-TYPE
	SYNTAX  Gauge
	ACCESS  read-only
	STATUS mandatory
	DESCRIPTION
	" The number of Background Block Errors
	 per interval of 24 hours."
	::= { gnMstMonDayEntry 4 }

gnMstMonDayUAS OBJECT-TYPE
	SYNTAX  Gauge
	ACCESS  read-only
	STATUS mandatory
	DESCRIPTION
	" The number of Unavailable Seconds
	 per interval of 24 hours."
	::= { gnMstMonDayEntry 5 }


gnMstFarEndMonCurrTable OBJECT-TYPE
	SYNTAX  SEQUENCE OF GnMstFarEndMonCurrEntry
	ACCESS  not-accessible
	STATUS mandatory
	DESCRIPTION
	"This table maintains the counters of the far end MST part of the MUX.
	This Table is not supported."
	::= { gnMstMon 4 }

gnMstFarEndMonCurrEntry OBJECT-TYPE
	SYNTAX GnMstFarEndMonCurrEntry
	ACCESS  not-accessible
	STATUS mandatory
	DESCRIPTION
	"This is an entry in the far end MST part of the MUX
	 Counters Table. This table contains an interface index for every interface
	 which type is SONET(39)."
	INDEX {  ifIndex }
	::= { gnMstFarEndMonCurrTable 1 }

GnMstFarEndMonCurrEntry ::=
	    SEQUENCE {
	--gnMstFarEndMonCurrES rfc1595
	--     Counter,
	--gnMstFarEndMonCurrSES
	--     Counter,
	gnMstFarEndMonCurrBBE
	     Gauge,
	gnMstFarEndMonCurrUAS
	     Gauge,
	gnMstFarEndMonCurrLastDayES
	     Gauge,
	gnMstFarEndMonCurrLastDaySES
	     Gauge,
	gnMstFarEndMonCurrLastDayBBE
	     Gauge,
	gnMstFarEndMonCurrLastDayUAS
	     Gauge
}



gnMstFarEndMonCurrBBE OBJECT-TYPE
	SYNTAX  Gauge
	ACCESS  read-only
	STATUS mandatory
	DESCRIPTION
	" The current number of Background Block Errors
	 starting from the present 15 minutes period."
	::= { gnMstFarEndMonCurrEntry 1}

gnMstFarEndMonCurrUAS OBJECT-TYPE
	SYNTAX  Gauge
	ACCESS  read-only
	STATUS mandatory
	DESCRIPTION
	" The current number of Unavailable Seconds
	 starting from the present 15 minutes period."
	::= { gnMstFarEndMonCurrEntry 2}


gnMstFarEndMonCurrLastDayES OBJECT-TYPE
	SYNTAX  Gauge
	ACCESS  read-only
	STATUS mandatory
	DESCRIPTION
	" The current number of Errored Seconds
	 starting from the present 24 hours period."
	::= { gnMstFarEndMonCurrEntry 3 }

gnMstFarEndMonCurrLastDaySES OBJECT-TYPE
	SYNTAX  Gauge
	ACCESS  read-only
	STATUS mandatory
	DESCRIPTION
	" The current number of Severely Errored Seconds
	 starting from the present 24 hours period."
	::= { gnMstFarEndMonCurrEntry 4 }

gnMstFarEndMonCurrLastDayBBE OBJECT-TYPE
	SYNTAX  Gauge
	ACCESS  read-only
	STATUS mandatory
	DESCRIPTION
	" The current number of Background Block Errors
	 starting from the present 24 hours period."
	::= { gnMstFarEndMonCurrEntry 5 }

gnMstFarEndMonCurrLastDayUAS OBJECT-TYPE
	SYNTAX  Gauge
	ACCESS  read-only
	STATUS mandatory
	DESCRIPTION
	" The current number of Unavailable Seconds
	 starting from the present 24 hours period."
	::= { gnMstFarEndMonCurrEntry 6 }


gnMstFarEndMonIntervalTable OBJECT-TYPE
	SYNTAX  SEQUENCE OF GnMstFarEndMonIntervalEntry
	ACCESS  not-accessible
	STATUS mandatory
	DESCRIPTION
	"This table maintains the counters of the far end MST part
	 of the MUX per interval.
	 This Table is not supported."
	::= { gnMstMon 5 }

gnMstFarEndMonIntervalEntry OBJECT-TYPE
	SYNTAX GnMstFarEndMonIntervalEntry
	ACCESS  not-accessible
	STATUS mandatory
	DESCRIPTION
	"This is an entry in the far end MST part of the MUX
	 Counters Table. This table contains an interface index for every interface
	 which type is SONET(39)
	This table is indexed by an interval index, between 1
	to 96 and representing each one 15 minutes.
               The oldest is 96."
	INDEX {  ifIndex, gnMstFarEndMonIntervalIdx}
	::= { gnMstFarEndMonIntervalTable 1 }

GnMstFarEndMonIntervalEntry ::=
	    SEQUENCE {
	gnMstFarEndMonIntervalIdx
	      INTEGER,
	--gnMstFarEndMonIntervalES
	--     Counter,
	--gnMstFarEndMonIntervalSES
	--     Counter,
	gnMstFarEndMonIntervalBBE
	     Gauge,
	gnMstFarEndMonIntervalUAS
	     Gauge
}

gnMstFarEndMonIntervalIdx OBJECT-TYPE
	SYNTAX INTEGER (1..96)
	ACCESS read-only
	STATUS mandatory
	DESCRIPTION
	"This table is indexed per interval number. Each interval
	is of 15 minutes and the oldest is 96."
	::= { gnMstFarEndMonIntervalEntry 1 }

gnMstFarEndMonIntervalBBE OBJECT-TYPE
	SYNTAX  Gauge
	ACCESS  read-only
	STATUS mandatory
	DESCRIPTION
	" The number of Background Block Errors
	per interval."
	::= { gnMstFarEndMonIntervalEntry 2}

gnMstFarEndMonIntervalUAS OBJECT-TYPE
	SYNTAX  Gauge
	ACCESS  read-only
	STATUS mandatory
	DESCRIPTION
	" The  number of Unavailable Seconds per interval."
	::= { gnMstFarEndMonIntervalEntry 3}


gnMstFarEndMonDayTable OBJECT-TYPE
	SYNTAX  SEQUENCE OF GnMstFarEndMonDayEntry
	ACCESS  not-accessible
	STATUS mandatory
	DESCRIPTION
	"This table maintains the counters of the far end MST part
     of the MUX per 24 hours interval.
     This Table is not supported."
	::= { gnMstMon 6 }

gnMstFarEndMonDayEntry OBJECT-TYPE
	SYNTAX GnMstFarEndMonDayEntry
	ACCESS  not-accessible
	STATUS mandatory
	DESCRIPTION
	"This is an entry in the far end MST part of the MUX
	 Counters Table. This table contains an interface index for every interface
	 which type is SONET(39).
	This table is indexed by an interval index, between 1
	to 30 and representing each one 24 hours.
               The oldest is 30."
	INDEX {  ifIndex, gnMstFarEndMonDayIdx}
	::= { gnMstFarEndMonDayTable 1 }

GnMstFarEndMonDayEntry ::=
	    SEQUENCE {
	gnMstFarEndMonDayIdx
	      INTEGER,
	gnMstFarEndMonDayES
	     Gauge,
	gnMstFarEndMonDaySES
	     Gauge,
	gnMstFarEndMonDayBBE
	     Gauge,
	gnMstFarEndMonDayUAS
	     Gauge
}

gnMstFarEndMonDayIdx OBJECT-TYPE
	SYNTAX INTEGER (1..30)
	ACCESS read-only
	STATUS mandatory
	DESCRIPTION
	"This table is indexed per interval number. Each interval
	is of 24 hours and the oldest is 30."
	::= { gnMstFarEndMonDayEntry 1 }

gnMstFarEndMonDayES OBJECT-TYPE
	SYNTAX  Gauge
	ACCESS  read-only
	STATUS mandatory
	DESCRIPTION
	" The number of Errored Seconds per interval of 24 hours."
	::= { gnMstFarEndMonDayEntry 2}

gnMstFarEndMonDaySES OBJECT-TYPE
	SYNTAX  Gauge
	ACCESS  read-only
	STATUS mandatory
	DESCRIPTION
	" The number of Severely Errored Seconds
	 per interval of 24 hours."
	::= { gnMstFarEndMonDayEntry 3}

gnMstFarEndMonDayBBE OBJECT-TYPE
	SYNTAX  Gauge
	ACCESS  read-only
	STATUS mandatory
	DESCRIPTION
	" The number of Background Block Errors
	 per interval of 24 hours."
	::= { gnMstFarEndMonDayEntry 4 }

gnMstFarEndMonDayUAS OBJECT-TYPE
	SYNTAX  Gauge
	ACCESS  read-only
	STATUS mandatory
	DESCRIPTION
	" The number of Unavailable Seconds
	 per interval of 24 hours."
	::= { gnMstFarEndMonDayEntry 5 }

-- HPT part of the MUX. All HPT tables are included for future development 
-- and are not currently implemented.
gnHptCfgTable OBJECT-TYPE
	SYNTAX  SEQUENCE OF GnHptCfgEntry
	ACCESS  not-accessible
	STATUS mandatory
	DESCRIPTION
	"This table maintains the counters of the HPT part
                of the MUX."
	::= { gnMux 7 }

gnHptCfgEntry OBJECT-TYPE
	SYNTAX GnHptCfgEntry
	ACCESS  not-accessible
	STATUS mandatory
	DESCRIPTION
	"This is an entry in the HPT part of the MUX
	 Configuration Table. This table contains an interface index for every 
interface
	 which type is PATH(50, according to RFC1573)."
	INDEX {  ifIndex }
	::= { gnHptCfgTable 1 }

GnHptCfgEntry ::=
	    SEQUENCE {
	gnHptCfgTransmittedJ1
	    DisplayString,
	gnHptCfgExpectedJ1
	     DisplayString,
	gnHptCfgMismatchJ1
	     INTEGER,
	gnHptCfgTransparencyJ1
		INTEGER,
	gnHptCfgEXCThresh
		INTEGER,
	gnHptCfgSDThresh
		INTEGER,
	gnHptCfgTug3Structure1
	     OCTET STRING,
	gnHptCfgTug3Structure2
	     OCTET STRING,
	gnHptCfgTug3Structure3
	     OCTET STRING,
	gnHptCfgSignalLabelMismatch
		INTEGER
}


gnHptCfgTransmittedJ1 OBJECT-TYPE
	SYNTAX  DisplayString (SIZE(0..15))
	ACCESS  read-write
	STATUS mandatory
	DESCRIPTION
	" This is the J1 string that would be sent."
	DEFVAL { "  ACCESS MUX   " }
	::= { gnHptCfgEntry 1 }

gnHptCfgExpectedJ1 OBJECT-TYPE
	SYNTAX  DisplayString (SIZE(0..15))
	ACCESS  read-write
	STATUS mandatory
	DESCRIPTION
  	" This is the J1 string that is expected to be received."
	DEFVAL { "  ACCESS MUX   " }
	::= { gnHptCfgEntry 2 }

gnHptCfgMismatchJ1 OBJECT-TYPE
        SYNTAX INTEGER{
                sendAlarm(2),
                sendAIS(3)
	}
	ACCESS  read-write
	STATUS mandatory
	DESCRIPTION
  	" In case of a J1 mismatch error, send or don't send AIS."
        DEFVAL { sendAlarm }
	::= { gnHptCfgEntry 3 }


gnHptCfgTransparencyJ1 OBJECT-TYPE
	SYNTAX  INTEGER {
			active(2),
			passthrough(3),
			notActive(4)
	}
	ACCESS  read-write
	STATUS mandatory
	DESCRIPTION
	" Send the received J1 string transparently or send the Transmitted J1
             configured string."
	DEFVAL { passthrough }
	::= { gnHptCfgEntry 4 }


gnHptCfgEXCThresh OBJECT-TYPE
	SYNTAX  INTEGER {
			tenExpMinus3(2),
			tenExpMinus4(3),
			tenExpMinus5(4)
	}
	ACCESS  read-write
	STATUS mandatory
	DESCRIPTION
	" If the bit error rate is higher than this threshold
	 an EXC alarm would be generated.
	EXC is for excessive."
	DEFVAL { tenExpMinus3}
	::= { gnHptCfgEntry 5 }

gnHptCfgSDThresh OBJECT-TYPE
	SYNTAX  INTEGER {
			tenExpMinus6(3),
			tenExpMinus7(4),
			tenExpMinus8(5),
			tenExpMinus9(6)
	}
	ACCESS  read-write
	STATUS mandatory
	DESCRIPTION
	" If the bit error rate is higher than this threshold
	 a SD alarm would be generated.
	SD is for Signal Degrade."
	DEFVAL { tenExpMinus6}
	::= { gnHptCfgEntry 6 }


gnHptCfgTug3Structure1 OBJECT-TYPE
	SYNTAX  OCTET STRING (SIZE(4))
	ACCESS  read-write
	STATUS mandatory
	DESCRIPTION
	"This field set the TUG-3 #1 structure: (hexadecimal number)
	the lsb 4 bits set VC12=0 or VC3=1 structure to the TUG3 #1. (the K of the KLM index is 1)
	for VC12 structure the next 21 bits (for SDH) or 28 bits (for SONET) set each of the VC12 
	to be blocked (bit is 0) or unblocked (bit is 1).
	if it is VC3 only one more bit indicates if it is blocked (0) or unblocked (1).
	if a VC12 is set to blocked (this is the default) the system will send TU-AIS in that VC12.
	it it is unblocked it will be path-through or mapped to a E1/T1 port (according to the gnAccessCfgLowPathIndex).
	the 21 or 28 bits order is as folwed (from lsb to msb direction): first 7 bits for M=1 (from KLM index),
	the next 7 bits for M=2, the next for M=3, and the last (only for SONET) for M=4.
	Example : SDH, VC12 strcture, blocked VCs: KLM=111,121 (M=1), 112,122 (M=2), 163,173 (M=3), unblocked VCs: all the other.
	the value in bits will be: 0011111 1111100 1111100 0000, and in Hexadecimal: 0x7FE7C0. (so enter: 00 7F E7 C0)."
	::= { gnHptCfgEntry 7 }

gnHptCfgTug3Structure2 OBJECT-TYPE
	SYNTAX  OCTET STRING (SIZE(4))
	ACCESS  read-write
	STATUS mandatory
	DESCRIPTION
	"This field set the TUG-3 #2 structure: (hexadecimal number)
	the lsb 4 bits set VC12=0 or VC3=1 structure to the TUG-3 #2. (the K of the KLM index is 2)
	for VC12 structure the next 21 bits (for SDH) or 28 bits (for SONET) set each of the VC12 
	to be blocked (bit is 0) or unblocked (bit is 1).
	if it is VC3 only one more bit indicates if it is blocked (0) or unblocked (1).
	if a VC12 is set to blocked (this is the default) the system will send TU-AIS in that VC12.
	it it is unblocked it will be path-through or mapped to a E1/T1 port (according to the gnAccessCfgLowPathIndex).
	the 21 or 28 bits order is as folwed (from lsb to msb direction): first 7 bits for M=1 (from KLM index),
	the next 7 bits for M=2, the next for M=3, and the last (only for SONET) for M=4.
	Example : SDH, VC12 strcture, blocked VCs: KLM=211,221 (M=1), 212,222 (M=2), 263,273 (M=3), unblocked VCs: all the other.
	the value in bits will be: 0011111 1111100 1111100 0000, and in Hexadecimal: 0x7FE7C0. (so enter: 00 7F E7 C0)."
	::= { gnHptCfgEntry 8 }

gnHptCfgTug3Structure3 OBJECT-TYPE
	SYNTAX  OCTET STRING (SIZE(4))
	ACCESS  read-write
	STATUS mandatory
	DESCRIPTION
	"This field set the TUG-3 #3 structure: (hexadecimal number)
	the lsb 4 bits set VC12=0 or VC3=1 structure to the TUG-3 #3. (the K of the KLM index is 3)
	for VC12 structure the next 21 bits (for SDH) or 28 bits (for SONET) set each of the VC12 
	to be blocked (bit is 0) or unblocked (bit is 1).
	if it is VC3 only one more bit indicates if it is blocked (0) or unblocked (1).
	if a VC12 is set to blocked (this is the default) the system will send TU-AIS in that VC12.
	it it is unblocked it will be path-through or mapped to a E1/T1 port (according to the gnAccessCfgLowPathIndex).
	the 21 or 28 bits order is as folwed (from lsb to msb direction): first 7 bits for M=1 (from KLM index),
	the next 7 bits for M=2, the next for M=3, and the last (only for SONET) for M=4.
	Example : SDH, VC12 strcture, blocked VCs: KLM=311,321 (M=1), 312,322 (M=2), 363,373 (M=3), unblocked VCs: all the other.
	the value in bits will be: 0011111 1111100 1111100 0000, and in Hexadecimal: 0x7FE7C0. (so enter: 00 7F E7 C0)."
	::= { gnHptCfgEntry 9 }

gnHptCfgSignalLabelMismatch OBJECT-TYPE
	SYNTAX  INTEGER{
		sendAlarm(2),
		sendAIS(3)
	}
        ACCESS  read-write
        STATUS mandatory
		DESCRIPTION
  		" In case of a C2 mismatch error, send or don't send AIS."
	    DEFVAL	{ sendAlarm }
        ::= { gnHptCfgEntry 10 }

gnHptStatTable OBJECT-TYPE
	SYNTAX  SEQUENCE OF GnHptStatEntry
	ACCESS  not-accessible
	STATUS mandatory
	DESCRIPTION
	"This table defines the status of the HPT part
                of the MUX."
	::= { gnMux 8 }

gnHptStatEntry OBJECT-TYPE
	SYNTAX GnHptStatEntry
	ACCESS  not-accessible
	STATUS mandatory
	DESCRIPTION
	"This is an entry in the HPT part of the MUX
	 Status Table. This table contains an interface index for every interface
	 which type is PATH(50, according to RFC1573)."
	INDEX {  ifIndex }
	::= { gnHptStatTable 1 }

GnHptStatEntry ::=
	    SEQUENCE {
	gnHptStatReceivedJ1
	     DisplayString,
	gnHptStatStatus
	     OCTET STRING,
--	gnHptStatFarEndStatus
--	     OCTET STRING,
	gnHptStatCurrentBer
		INTEGER,
	gnHptStatFarEndCurrentBer
		INTEGER,
	gnHptStatReceivedSignalLabel
	     OCTET STRING
}

gnHptStatReceivedJ1 OBJECT-TYPE
	SYNTAX  DisplayString(SIZE(0..15))
	ACCESS  read-only
	STATUS mandatory
	DESCRIPTION
	"This is the J1 string that was received."
	::= { gnHptStatEntry 1 }

gnHptStatStatus OBJECT-TYPE
	SYNTAX OCTET STRING(SIZE(2))
	ACCESS  read-only
	STATUS mandatory
	DESCRIPTION
	 "Alarm status byte. Bit 1 is MSB, bit=1 when alarm active.
	  bit 4  = LOP
	  bit 5  = RDI
	  bit 6  = AIS
	  bit 7  = TIM
	  bit 8  = SLM/PLM
	  bit 9  = SD
	  bit 10 = EXC
	  bit 12 = UNEQ
	  bit 15 = LOM"
	::= { gnHptStatEntry 2 }

--gnHptStatFarEndStatus OBJECT-TYPE
--	SYNTAX OCTET STRING(SIZE(2))
--	ACCESS  read-only
--	STATUS mandatory
--	DESCRIPTION
--	 "Alarm status byte. Bit 1 is MSB, bit=1 when alarm active.
--	  bit 5  = RDI"
--	::= { gnHptStatEntry 3 }

gnHptStatCurrentBer OBJECT-TYPE
	SYNTAX  INTEGER {
			tenExpMinus3(2),
			tenExpMinus4(3),
			tenExpMinus5(4),
			tenExpMinus6(5),
			tenExpMinus7(6),
			tenExpMinus8(7),
			tenExpMinus9(8),
			tenExpMinus10(9),
			tenExpMinus11(10),
			tenExpMinus12(11),
			tenExpMinus13(12),
			tenExpMinus14(13)
	}
	ACCESS  read-only
	STATUS mandatory
	DESCRIPTION
	" "
	::= { gnHptStatEntry 3 }

gnHptStatFarEndCurrentBer OBJECT-TYPE
	SYNTAX  INTEGER {
			tenExpMinus3(2),
			tenExpMinus4(3),
			tenExpMinus5(4),
			tenExpMinus6(5),
			tenExpMinus7(6),
			tenExpMinus8(7),
			tenExpMinus9(8),
			tenExpMinus10(9),
			tenExpMinus11(10),
			tenExpMinus12(11),
			tenExpMinus13(12),
			tenExpMinus14(13)
	}
	ACCESS  read-only
	STATUS mandatory
	DESCRIPTION
	" "
	::= { gnHptStatEntry 4 }

gnHptStatReceivedSignalLabel OBJECT-TYPE
	SYNTAX OCTET STRING(SIZE(1))
	ACCESS  read-only
	STATUS mandatory
	DESCRIPTION
	"This is the C2 string that was received."
	::= { gnHptStatEntry 5 }


-- Statistics For HPT. All HPT tables are included for future development 
-- and are not currently implemented.
gnHptMon OBJECT IDENTIFIER ::=  { gnMux 9 }

gnHptMonCurrTable OBJECT-TYPE
	SYNTAX  SEQUENCE OF GnHptMonCurrEntry
	ACCESS  not-accessible
	STATUS mandatory
	DESCRIPTION
	"This table maintains the counters of the HPT part
                of the MUX."
	::= { gnHptMon 1 }

gnHptMonCurrEntry OBJECT-TYPE
	SYNTAX GnHptMonCurrEntry
	ACCESS  not-accessible
	STATUS mandatory
	DESCRIPTION
	"This is an entry in the HPT part of the MUX
	 Counters Table. This table contains an interface index for every interface
	 which type is PATH(50, according to RFC1573)."
	INDEX {  ifIndex }
	::= { gnHptMonCurrTable 1 }

GnHptMonCurrEntry ::=
	    SEQUENCE {
	--gnHptMonCurrES rfc1595
	--     Counter,
	--gnHptMonCurrSES
	--     Counter,
	gnHptMonCurrBBE
	     Gauge,
	gnHptMonCurrUAS
	     Gauge,
	gnHptMonCurrLastDayES
	     Gauge,
	gnHptMonCurrLastDaySES
	     Gauge,
	gnHptMonCurrLastDayBBE
	     Gauge,
	gnHptMonCurrLastDayUAS
	     Gauge
}



gnHptMonCurrBBE OBJECT-TYPE
	SYNTAX  Gauge
	ACCESS  read-only
	STATUS mandatory
	DESCRIPTION
	" The current number of Background Block Errors
	 starting  from the present 15 minutes period."
	::= { gnHptMonCurrEntry 1}

gnHptMonCurrUAS OBJECT-TYPE
	SYNTAX  Gauge
	ACCESS  read-only
	STATUS mandatory
	DESCRIPTION
	" The current number of Unavailable Seconds
	 starting  from the present 15 minutes period."
	::= { gnHptMonCurrEntry 2}


gnHptMonCurrLastDayES OBJECT-TYPE
	SYNTAX  Gauge
	ACCESS  read-only
	STATUS mandatory
	DESCRIPTION
	" The current number of Errored Seconds
	 starting from the present 24 hours period."
	::= { gnHptMonCurrEntry 3 }

gnHptMonCurrLastDaySES OBJECT-TYPE
	SYNTAX  Gauge
	ACCESS  read-only
	STATUS mandatory
	DESCRIPTION
	" The current number of Severely Errored Seconds
	 starting from the present 24 hours period."
	::= { gnHptMonCurrEntry 4 }

gnHptMonCurrLastDayBBE OBJECT-TYPE
	SYNTAX  Gauge
	ACCESS  read-only
	STATUS mandatory
	DESCRIPTION
	" The current number of Background Block Errors
	 starting from the present 24 hours period."
	::= { gnHptMonCurrEntry 5 }

gnHptMonCurrLastDayUAS OBJECT-TYPE
	SYNTAX  Gauge
	ACCESS  read-only
	STATUS mandatory
	DESCRIPTION
	" The current number of Unavailable  Seconds
	 starting from the present 24 hours period."
	::= { gnHptMonCurrEntry 6 }


gnHptMonIntervalTable OBJECT-TYPE
	SYNTAX  SEQUENCE OF GnHptMonIntervalEntry
	ACCESS  not-accessible
	STATUS mandatory
	DESCRIPTION
	"This table maintains the counters of the HPT part
                of the MUX per interval."
	::= { gnHptMon 2 }

gnHptMonIntervalEntry OBJECT-TYPE
	SYNTAX GnHptMonIntervalEntry
	ACCESS  not-accessible
	STATUS mandatory
	DESCRIPTION
	"This is an entry in the HPT part of the MUX
	 Counters Table. This table contains an interface index for every interface
	 which type is PATH(50, according to RFC1573).
	This table is indexed by an interval index, between 1
	to 96 and representing each one 15 minutes.
               The oldest is 96."
	INDEX {  ifIndex, gnHptMonIntervalIdx}
	::= { gnHptMonIntervalTable 1 }

GnHptMonIntervalEntry ::=
	    SEQUENCE {
	gnHptMonIntervalIdx
	      INTEGER,
	--gnHptMonIntervalES
	--     Counter,
	--gnHptMonIntervalSES
	--     Counter,
	gnHptMonIntervalBBE
	     Gauge,
	gnHptMonIntervalUAS
	     Gauge
}

gnHptMonIntervalIdx OBJECT-TYPE
	SYNTAX INTEGER (1..96)
	ACCESS read-only
	STATUS mandatory
	DESCRIPTION
	"This table is indexed per interval number. Each interval
	is of 15 minutes and the oldest is 96."
	::= { gnHptMonIntervalEntry 1 }

gnHptMonIntervalBBE OBJECT-TYPE
	SYNTAX  Gauge
	ACCESS  read-only
	STATUS mandatory
	DESCRIPTION
	" The number of Background Block Errors
	per interval."
	::= { gnHptMonIntervalEntry 2}

gnHptMonIntervalUAS OBJECT-TYPE
	SYNTAX  Gauge
	ACCESS  read-only
	STATUS mandatory
	DESCRIPTION
	" The  number of Unavailable Seconds per interval."
	::= { gnHptMonIntervalEntry 3}


gnHptMonDayTable OBJECT-TYPE
	SYNTAX  SEQUENCE OF GnHptMonDayEntry
	ACCESS  not-accessible
	STATUS mandatory
	DESCRIPTION
	"This table maintains the counters of the HPT part
                of the MUX per 24 hours interval."
	::= { gnHptMon 3 }

gnHptMonDayEntry OBJECT-TYPE
	SYNTAX GnHptMonDayEntry
	ACCESS  not-accessible
	STATUS mandatory
	DESCRIPTION
	"This is an entry in the HPT part of the MUX
	 Counters Table. This table contains an interface index for every interface
	 which type is PATH(50, according to RFC1573).
	This table is indexed by an interval index, between 1
	to 30 and representing each one 24 hours.
               The oldest is 30."
	INDEX {  ifIndex, gnHptMonDayIdx}
	::= { gnHptMonDayTable 1 }

GnHptMonDayEntry ::=
	    SEQUENCE {
	gnHptMonDayIdx
	      INTEGER,
	gnHptMonDayES
	     Gauge,
	gnHptMonDaySES
	     Gauge,
	gnHptMonDayBBE
	     Gauge,
	gnHptMonDayUAS
	     Gauge
}

gnHptMonDayIdx OBJECT-TYPE
	SYNTAX INTEGER (1..30)
	ACCESS read-only
	STATUS mandatory
	DESCRIPTION
	"This table is indexed per interval number. Each interval
	is of 24 hours and the oldest is 30."
	::= { gnHptMonDayEntry 1 }

gnHptMonDayES OBJECT-TYPE
	SYNTAX  Gauge
	ACCESS  read-only
	STATUS mandatory
	DESCRIPTION
	" The number of Errored Seconds per interval of 24 hours."
	::= { gnHptMonDayEntry 2}

gnHptMonDaySES OBJECT-TYPE
	SYNTAX  Gauge
	ACCESS  read-only
	STATUS mandatory
	DESCRIPTION
	" The number of Severely Errored Seconds
	 per interval of 24 hours."
	::= { gnHptMonDayEntry 3}

gnHptMonDayBBE OBJECT-TYPE
	SYNTAX  Gauge
	ACCESS  read-only
	STATUS mandatory
	DESCRIPTION
	" The number of Background Block Errors
	 per interval of 24 hours."
	::= { gnHptMonDayEntry 4 }

gnHptMonDayUAS OBJECT-TYPE
	SYNTAX  Gauge
	ACCESS  read-only
	STATUS mandatory
	DESCRIPTION
	" The number of Unavailable Seconds
	 per interval of 24 hours."
	::= { gnHptMonDayEntry 5 }


gnHptFarEndMonCurrTable OBJECT-TYPE
	SYNTAX  SEQUENCE OF GnHptFarEndMonCurrEntry
	ACCESS  not-accessible
	STATUS mandatory
	DESCRIPTION
	"This table maintains the counters of the far end HPT part
                of the MUX."
	::= { gnHptMon 4 }

gnHptFarEndMonCurrEntry OBJECT-TYPE
	SYNTAX GnHptFarEndMonCurrEntry
	ACCESS  not-accessible
	STATUS mandatory
	DESCRIPTION
	"This is an entry in the far end HPT part of the MUX
	 Counters Table. This table contains an interface index for every interface
	 which type is PATH(50, according to RFC1573)."
	INDEX {  ifIndex }
	::= { gnHptFarEndMonCurrTable 1 }

GnHptFarEndMonCurrEntry ::=
	    SEQUENCE {
	--gnHptFarEndMonCurrES rfc1595
	--     Counter,
	--gnHptFarEndMonCurrSES
	--     Counter,
	gnHptFarEndMonCurrBBE
	     Gauge,
	gnHptFarEndMonCurrUAS
	     Gauge,
	gnHptFarEndMonCurrLastDayES
	     Gauge,
	gnHptFarEndMonCurrLastDaySES
	     Gauge,
	gnHptFarEndMonCurrLastDayBBE
	     Gauge,
	gnHptFarEndMonCurrLastDayUAS
	     Gauge
}



gnHptFarEndMonCurrBBE OBJECT-TYPE
	SYNTAX  Gauge
	ACCESS  read-only
	STATUS mandatory
	DESCRIPTION
	" The current number of Background Block Errors
	 starting from the present 15 minutes period."
	::= { gnHptFarEndMonCurrEntry 1}

gnHptFarEndMonCurrUAS OBJECT-TYPE
	SYNTAX  Gauge
	ACCESS  read-only
	STATUS mandatory
	DESCRIPTION
	" The current number of Unavailable Seconds
	 starting from the present 15 minutes period."
	::= { gnHptFarEndMonCurrEntry 2}


gnHptFarEndMonCurrLastDayES OBJECT-TYPE
	SYNTAX  Gauge
	ACCESS  read-only
	STATUS mandatory
	DESCRIPTION
	" The current number of Errored Seconds
	 starting from the present 24 hours period."
	::= { gnHptFarEndMonCurrEntry 3 }

gnHptFarEndMonCurrLastDaySES OBJECT-TYPE
	SYNTAX  Gauge
	ACCESS  read-only
	STATUS mandatory
	DESCRIPTION
	" The current number of Severely Errored Seconds
	 starting from the present 24 hours period."
	::= { gnHptFarEndMonCurrEntry 4 }

gnHptFarEndMonCurrLastDayBBE OBJECT-TYPE
	SYNTAX  Gauge
	ACCESS  read-only
	STATUS mandatory
	DESCRIPTION
	" The current number of Background Block Errors
	 starting 	from the present 24 hours period."
	::= { gnHptFarEndMonCurrEntry 5 }

gnHptFarEndMonCurrLastDayUAS OBJECT-TYPE
	SYNTAX  Gauge
	ACCESS  read-only
	STATUS mandatory
	DESCRIPTION
	" The current number of Unavailable  Seconds
	 starting 	from the present 24 hours period."
	::= { gnHptFarEndMonCurrEntry 6 }


gnHptFarEndMonIntervalTable OBJECT-TYPE
	SYNTAX  SEQUENCE OF GnHptFarEndMonIntervalEntry
	ACCESS  not-accessible
	STATUS mandatory
	DESCRIPTION
	"This table maintains the counters of the far end HPT part
                of the MUX per interval."
	::= { gnHptMon 5 }

gnHptFarEndMonIntervalEntry OBJECT-TYPE
	SYNTAX GnHptFarEndMonIntervalEntry
	ACCESS  not-accessible
	STATUS mandatory
	DESCRIPTION
	"This is an entry in the far end HPT part of the MUX
	 Counters Table. This table contains an interface index for every interface
	 which type is PATH(50, according to RFC1573).
	This table is indexed by an interval index, between 1
	to 96 and representing each one 15 minutes.
               The oldest is 96."
	INDEX {  ifIndex, gnHptFarEndMonIntervalIdx}
	::= { gnHptFarEndMonIntervalTable 1 }

GnHptFarEndMonIntervalEntry ::=
	    SEQUENCE {
	gnHptFarEndMonIntervalIdx
	      INTEGER,
	--gnHptFarEndMonIntervalES
	--     Counter,
	--gnHptFarEndMonIntervalSES
	--     Counter,
	gnHptFarEndMonIntervalBBE
	     Gauge,
	gnHptFarEndMonIntervalUAS
	     Gauge
}

gnHptFarEndMonIntervalIdx OBJECT-TYPE
	SYNTAX INTEGER (1..96)
	ACCESS read-only
	STATUS mandatory
	DESCRIPTION
	"This table is indexed per interval number. Each interval
	is of 15 minutes and the oldest is 96."
	::= { gnHptFarEndMonIntervalEntry 1 }

gnHptFarEndMonIntervalBBE OBJECT-TYPE
	SYNTAX  Gauge
	ACCESS  read-only
	STATUS mandatory
	DESCRIPTION
	" The number of Background Block Errors
	per interval."
	::= { gnHptFarEndMonIntervalEntry 2}

gnHptFarEndMonIntervalUAS OBJECT-TYPE
	SYNTAX  Gauge
	ACCESS  read-only
	STATUS mandatory
	DESCRIPTION
	" The  number of Unavailable Seconds per interval."
	::= { gnHptFarEndMonIntervalEntry 3}


gnHptFarEndMonDayTable OBJECT-TYPE
	SYNTAX  SEQUENCE OF GnHptFarEndMonDayEntry
	ACCESS  not-accessible
	STATUS mandatory
	DESCRIPTION
	"This table maintains the counters of the far end HPT part
                of the MUX per 24 hours interval."
	::= { gnHptMon 6 }

gnHptFarEndMonDayEntry OBJECT-TYPE
	SYNTAX GnHptFarEndMonDayEntry
	ACCESS  not-accessible
	STATUS mandatory
	DESCRIPTION
	"This is an entry in the far end HPT part of the MUX
	 Counters Table. This table contains an interface index for every interface
	 which type is PATH(50, according to RFC1573).
	This table is indexed by an interval index, between 1
	to 30 and representing each one 24 hours.
               The oldest is 30."
	INDEX {  ifIndex, gnHptFarEndMonDayIdx}
	::= { gnHptFarEndMonDayTable 1 }

GnHptFarEndMonDayEntry ::=
	    SEQUENCE {
	gnHptFarEndMonDayIdx
	      INTEGER,
	gnHptFarEndMonDayES
	     Gauge,
	gnHptFarEndMonDaySES
	     Gauge,
	gnHptFarEndMonDayBBE
	     Gauge,
	gnHptFarEndMonDayUAS
	     Gauge
}

gnHptFarEndMonDayIdx OBJECT-TYPE
	SYNTAX INTEGER (1..30)
	ACCESS read-only
	STATUS mandatory
	DESCRIPTION
	"This table is indexed per interval number. Each interval
	is of 24 hours and the oldest is 30."
	::= { gnHptFarEndMonDayEntry 1 }

gnHptFarEndMonDayES OBJECT-TYPE
	SYNTAX  Gauge
	ACCESS  read-only
	STATUS mandatory
	DESCRIPTION
	" The number of Errored Seconds per interval of 24 hours."
	::= { gnHptFarEndMonDayEntry 2}

gnHptFarEndMonDaySES OBJECT-TYPE
	SYNTAX  Gauge
	ACCESS  read-only
	STATUS mandatory
	DESCRIPTION
	" The number of Severely Errored Seconds
	 per interval of 24 hours."
	::= { gnHptFarEndMonDayEntry 3}

gnHptFarEndMonDayBBE OBJECT-TYPE
	SYNTAX  Gauge
	ACCESS  read-only
	STATUS mandatory
	DESCRIPTION
	" The number of Background Block Errors
	 per interval of 24 hours."
	::= { gnHptFarEndMonDayEntry 4 }

gnHptFarEndMonDayUAS OBJECT-TYPE
	SYNTAX  Gauge
	ACCESS  read-only
	STATUS mandatory
	DESCRIPTION
	" The number of Unavailable Seconds
	 per interval of 24 hours."
	::= { gnHptFarEndMonDayEntry 5 }

-- LPT part of the MUX. All LPT tables are included for future development 
-- and are not currently implemented.
gnLptCfgTable OBJECT-TYPE
	SYNTAX  SEQUENCE OF GnLptCfgEntry
	ACCESS  not-accessible
	STATUS mandatory
	DESCRIPTION
	"This table maintains the counters of the LPT part
                of the MUX."
	::= { gnMux 10 }

gnLptCfgEntry OBJECT-TYPE
	SYNTAX GnLptCfgEntry
	ACCESS  not-accessible
	STATUS mandatory
	DESCRIPTION
	"This is an entry in the LPT part of the MUX
	 Configuration Table. This table contains an interface index for every 
	interface	 which type is VT(51, according to RFC1573)."
	INDEX {  ifIndex }
	::= { gnLptCfgTable 1 }

GnLptCfgEntry ::=
	    SEQUENCE {
--	gnLptCfgTransmittedC2
--	 INTEGER,
--	gnLptCfgExpectedC2
--	   INTEGER,
--	gnLptCfgMismatchC2
--	    INTEGER,
--	gnLptCfgTransmittedJ1
--	    DisplayString,
--	gnLptCfgExpectedJ1
--	     DisplayString,
--	gnLptCfgMismatchJ1
--	     INTEGER,
	gnLptCfgEXCThresh
	     INTEGER,
	gnLptCfgSDThresh
	     INTEGER
}

--gnLptCfgTransmittedC2 OBJECT-TYPE
--	SYNTAX  INTEGER
--	ACCESS  read-write
--	STATUS mandatory
--	DESCRIPTION
--	"This is the C2 byte that would be sent."
--	DEFVAL { '02'H}
--	::= { gnLptCfgEntry 1 }

--gnLptCfgExpectedC2 OBJECT-TYPE
--	SYNTAX  INTEGER
--	ACCESS  read-write
--	STATUS mandatory
--	DESCRIPTION
--	"This is the C2 byte that is expected to be received."
--	DEFVAL { '02'H}
--	::= { gnLptCfgEntry 2 }

--gnLptCfgMismatchC2 OBJECT-TYPE
--	SYNTAX  INTEGER{
--		sendAIS(2),
--		doNotSendAIS(3)
--	}
--	ACCESS  read-write
--	STATUS mandatory
--	DESCRIPTION
--	" In case of  C2 mismatch  error, send or don't send AIS."
--	DEFVAL { sendAIS }
--	::= { gnLptCfgEntry 3 }

--gnLptCfgTransmittedJ1 OBJECT-TYPE
--	SYNTAX  DisplayString(SIZE(0..63))
--	ACCESS  read-write
--	STATUS mandatory
--	DESCRIPTION
--	"This is the J1 string that would be sent."
--	DEFVAL { "" }
--	::= { gnLptCfgEntry 4 }

--gnLptCfgExpectedJ1 OBJECT-TYPE
--	SYNTAX  DisplayString(SIZE(0..63))
--	ACCESS  read-write
--	STATUS mandatory
--	DESCRIPTION
--  	"This is the J1 string that is expected to be received."
--	DEFVAL { "" }
--	::= { gnLptCfgEntry 5 }

--gnLptCfgMismatchJ1 OBJECT-TYPE
--	SYNTAX INTEGER{
--                transparency(2),
--                sendAlarm(3),
--                sendAIS(4)
--	}
--	ACCESS  read-write
--	STATUS mandatory
--	DESCRIPTION
--  	" In case of  J1 mismatch  error send or don't send AIS."
--	DEFVAL { transparency }
--	::= { gnLptCfgEntry 6 }

-- NOT IMPLEMENTED (access):
gnLptCfgEXCThresh  OBJECT-TYPE
	SYNTAX  INTEGER {
			tenExpMinus3(2),
			tenExpMinus4(3),
			tenExpMinus5(4)
	}
	ACCESS  read-write
	STATUS mandatory
	DESCRIPTION
	" If the bit error rate is higher than this threshold
	 an alarm would be generated.
	EXC is for excessive."
	DEFVAL { tenExpMinus3}
	::= { gnLptCfgEntry 1 }

-- NOT IMPLEMENTED (access):
gnLptCfgSDThresh  OBJECT-TYPE
	SYNTAX  INTEGER {
			tenExpMinus6(3),
			tenExpMinus7(4),
			tenExpMinus8(5),
			tenExpMinus9(6)
	}
	ACCESS  read-write
	STATUS mandatory
	DESCRIPTION
	" If the bit error rate is higher than this threshold
	 an alarm would be generated.
	SD is for Signal Degrade."
	DEFVAL { tenExpMinus6}
	::= { gnLptCfgEntry 2 }

gnLptStatTable OBJECT-TYPE
	SYNTAX  SEQUENCE OF GnLptStatEntry
	ACCESS  not-accessible
	STATUS mandatory
	DESCRIPTION
	"This table defines the status of the LPT part
                of the MUX."
	::= { gnMux 11 }

gnLptStatEntry OBJECT-TYPE
	SYNTAX GnLptStatEntry
	ACCESS  not-accessible
	STATUS mandatory
	DESCRIPTION
	"This is an entry in the LPT part of the MUX
	 Status Table. This table contains an interface index for every interface
	 which type is VT(51, according to RFC1573)."
	INDEX {  ifIndex }
	::= { gnLptStatTable 1 }

GnLptStatEntry ::=
	    SEQUENCE {
	gnLptStatReceivedJ2
	     DisplayString,
	gnLptStatStatus
		OCTET STRING,
--	gnLptStatFarEndStatus
--		OCTET STRING,
	gnLptStatProtectionMode
		INTEGER,
	gnLptStatCurrentBer
		INTEGER,
	gnLptStatFarEndCurrentBer
		INTEGER,
	gnLptStatReceivedSignalLabel
	     OCTET STRING,
	gnLptStatKLM
		INTEGER
}

gnLptStatReceivedJ2 OBJECT-TYPE
	SYNTAX  DisplayString(SIZE(0..15))
	ACCESS  read-only
	STATUS mandatory
	DESCRIPTION
	"This is the J2 string that was received."
	::= { gnLptStatEntry 1 }

gnLptStatStatus OBJECT-TYPE
	SYNTAX OCTET STRING(SIZE(2))
	ACCESS  read-only
	STATUS mandatory
	DESCRIPTION
	 "Alarm status byte. Bit 1 is MSB, bit=1 when alarm active.
	  bit 4  = LOP
	  bit 5  = RDI
	  bit 6  = AIS
	  bit 7  = TIM
	  bit 8  = SLM/PLM
	  bit 9  = SD
	  bit 10 = EXC
	  bit 12 = UNEQ"
	::= { gnLptStatEntry 2 }

--gnLptStatFarEndStatus OBJECT-TYPE
--	SYNTAX OCTET STRING(SIZE(2))
--	ACCESS  read-only
--	STATUS mandatory
--	DESCRIPTION
--	"bit 5  = RDI"
--	::= { gnLptStatEntry 3 }

gnLptStatProtectionMode OBJECT-TYPE
	SYNTAX  INTEGER {
		working(2),
        protect(3),
		passthrough(4),
		notActive(5)
	}
	ACCESS  read-only
	STATUS mandatory
	DESCRIPTION
	" "
	::= { gnLptStatEntry 3 }

gnLptStatCurrentBer OBJECT-TYPE
	SYNTAX  INTEGER {
			tenExpMinus3(2),
			tenExpMinus4(3),
			tenExpMinus5(4),
			tenExpMinus6(5),
			tenExpMinus7(6),
			tenExpMinus8(7),
			tenExpMinus9(8),
			tenExpMinus10(9),
			tenExpMinus11(10),
			tenExpMinus12(11),
			tenExpMinus13(12),
			tenExpMinus14(13)
	}
	ACCESS  read-only
	STATUS mandatory
	DESCRIPTION
	" "
	::= { gnLptStatEntry 4 }

gnLptStatFarEndCurrentBer OBJECT-TYPE
	SYNTAX  INTEGER {
			tenExpMinus3(2),
			tenExpMinus4(3),
			tenExpMinus5(4),
			tenExpMinus6(5),
			tenExpMinus7(6),
			tenExpMinus8(7),
			tenExpMinus9(8),
			tenExpMinus10(9),
			tenExpMinus11(10),
			tenExpMinus12(11),
			tenExpMinus13(12),
			tenExpMinus14(13)
	}
	ACCESS  read-only
	STATUS mandatory
	DESCRIPTION
	" "
	::= { gnLptStatEntry 5 }

gnLptStatReceivedSignalLabel OBJECT-TYPE
	SYNTAX OCTET STRING(SIZE(1))
	ACCESS  read-only
	STATUS mandatory
	DESCRIPTION
	"These are bits 1..3 of the V5 string that was received
	 (bit 0 is the lsb)."
	::= { gnLptStatEntry 6 }

gnLptStatKLM OBJECT-TYPE
	SYNTAX  INTEGER 
	ACCESS  read-only
	STATUS  mandatory
	DESCRIPTION
	" "
	::= { gnLptStatEntry 7 }


gnLptMon OBJECT IDENTIFIER ::=  { gnMux 12 }

gnLptMonCurrTable OBJECT-TYPE
	SYNTAX  SEQUENCE OF GnLptMonCurrEntry
	ACCESS  not-accessible
	STATUS mandatory
	DESCRIPTION
	"This table maintains the counters of the LPT part
                of the MUX."
	::= { gnLptMon 1 }

gnLptMonCurrEntry OBJECT-TYPE
	SYNTAX GnLptMonCurrEntry
	ACCESS  not-accessible
	STATUS mandatory
	DESCRIPTION
	"This is an entry in the LPT part of the MUX
	 Counters Table. This table contains an interface index for every interface
	 which type is VT(51, according to RFC1573)."
	INDEX {  ifIndex }
	::= { gnLptMonCurrTable 1 }

GnLptMonCurrEntry ::=
	    SEQUENCE {
	--gnLptMonCurrES rfc1595
	--     Counter,
	--gnLptMonCurrSES
	--     Counter,
	gnLptMonCurrBBE
	     Gauge,
	gnLptMonCurrUAS
	     Gauge,
	gnLptMonCurrLastDayES
	     Gauge,
	gnLptMonCurrLastDaySES
	     Gauge,
	gnLptMonCurrLastDayBBE
	     Gauge,
	gnLptMonCurrLastDayUAS
	     Gauge
}



gnLptMonCurrBBE OBJECT-TYPE
	SYNTAX  Gauge
	ACCESS  read-only
	STATUS mandatory
	DESCRIPTION
	" The current number of Background Block Errors
	 starting  from the present 15 minutes period."
	::= { gnLptMonCurrEntry 1}

gnLptMonCurrUAS OBJECT-TYPE
	SYNTAX  Gauge
	ACCESS  read-only
	STATUS mandatory
	DESCRIPTION
	" The current number of Unavailable Seconds
	 starting from the present 15 minutes period."
	::= { gnLptMonCurrEntry 2}


gnLptMonCurrLastDayES OBJECT-TYPE
	SYNTAX  Gauge
	ACCESS  read-only
	STATUS mandatory
	DESCRIPTION
	" The current number of Errored Seconds
	 starting from the present 24 hours period."
	::= { gnLptMonCurrEntry 3 }

gnLptMonCurrLastDaySES OBJECT-TYPE
	SYNTAX  Gauge
	ACCESS  read-only
	STATUS mandatory
	DESCRIPTION
	" The current number of Severely Errored Seconds
	 starting from the present 24 hours period."
	::= { gnLptMonCurrEntry 4 }

gnLptMonCurrLastDayBBE OBJECT-TYPE
	SYNTAX  Gauge
	ACCESS  read-only
	STATUS mandatory
	DESCRIPTION
	" The current number of Background Block Errors
	 starting 	from the present 24 hours period."
	::= { gnLptMonCurrEntry 5 }

gnLptMonCurrLastDayUAS OBJECT-TYPE
	SYNTAX  Gauge
	ACCESS  read-only
	STATUS mandatory
	DESCRIPTION
	" The current number of Unavailable  Seconds
	 starting 	from the present 24 hours period."
	::= { gnLptMonCurrEntry 6 }


gnLptMonIntervalTable OBJECT-TYPE
	SYNTAX  SEQUENCE OF GnLptMonIntervalEntry
	ACCESS  not-accessible
	STATUS mandatory
	DESCRIPTION
	"This table maintains the counters of the LPT part
                of the MUX per interval."
	::= { gnLptMon 2 }

gnLptMonIntervalEntry OBJECT-TYPE
	SYNTAX GnLptMonIntervalEntry
	ACCESS  not-accessible
	STATUS mandatory
	DESCRIPTION
	"This is an entry in the LPT part of the MUX
	 Counters Table. This table contains an interface index for every interface
	 which type is VT(51, according to RFC1573).
	This table is indexed by an interval index, between 1
	to 96 and representing each one 15 minutes.
               The oldest is 96."
	INDEX {  ifIndex, gnLptMonIntervalIdx}
	::= { gnLptMonIntervalTable 1 }

GnLptMonIntervalEntry ::=
	    SEQUENCE {
	gnLptMonIntervalIdx
	      INTEGER,
	--gnLptMonIntervalES
	--     Counter,
	--gnLptMonIntervalSES
	--     Counter,
	gnLptMonIntervalBBE
	     Gauge,
	gnLptMonIntervalUAS
	     Gauge
}

gnLptMonIntervalIdx OBJECT-TYPE
	SYNTAX INTEGER (1..96)
	ACCESS read-only
	STATUS mandatory
	DESCRIPTION
	"This table is indexed per interval number. Each interval
	is of 15 minutes and the oldest is 96."
	::= { gnLptMonIntervalEntry 1 }

gnLptMonIntervalBBE OBJECT-TYPE
	SYNTAX  Gauge
	ACCESS  read-only
	STATUS mandatory
	DESCRIPTION
	" The number of Background Block Errors
	per interval."
	::= { gnLptMonIntervalEntry 2}

gnLptMonIntervalUAS OBJECT-TYPE
	SYNTAX  Gauge
	ACCESS  read-only
	STATUS mandatory
	DESCRIPTION
	" The  number of Unavailable Seconds per interval."
	::= { gnLptMonIntervalEntry 3}


gnLptMonDayTable OBJECT-TYPE
	SYNTAX  SEQUENCE OF GnLptMonDayEntry
	ACCESS  not-accessible
	STATUS mandatory
	DESCRIPTION
	"This table maintains the counters of the LPT part
                of the MUX per 24 hours interval."
	::= { gnLptMon 3 }

gnLptMonDayEntry OBJECT-TYPE
	SYNTAX GnLptMonDayEntry
	ACCESS  not-accessible
	STATUS mandatory
	DESCRIPTION
	"This is an entry in the LPT part of the MUX
	 Counters Table. This table contains four groups of rows,
	indexed by ifIndex= 1,2 for local IDU and
	ifIndex = 101 and 102 for remote IDU.
	This table is indexed by an interval index, between 1
	to 30 and representing each one 24 hours.
               The oldest is 30."
	INDEX {  ifIndex, gnLptMonDayIdx}
	::= { gnLptMonDayTable 1 }

GnLptMonDayEntry ::=
	    SEQUENCE {
	gnLptMonDayIdx
	      INTEGER,
	gnLptMonDayES
	     Gauge,
	gnLptMonDaySES
	     Gauge,
	gnLptMonDayBBE
	     Gauge,
	gnLptMonDayUAS
	     Gauge
}

gnLptMonDayIdx OBJECT-TYPE
	SYNTAX INTEGER (1..30)
	ACCESS read-only
	STATUS mandatory
	DESCRIPTION
	"This table is indexed per interval number. Each interval
	is of 24 hours and the oldest is 30."
	::= { gnLptMonDayEntry 1 }

gnLptMonDayES OBJECT-TYPE
	SYNTAX  Gauge
	ACCESS  read-only
	STATUS mandatory
	DESCRIPTION
	" The number of Errored Seconds per interval of 24 hours."
	::= { gnLptMonDayEntry 2}

gnLptMonDaySES OBJECT-TYPE
	SYNTAX  Gauge
	ACCESS  read-only
	STATUS mandatory
	DESCRIPTION
	" The number of Severely Errored Seconds
	 per interval of 24 hours."
	::= { gnLptMonDayEntry 3}

gnLptMonDayBBE OBJECT-TYPE
	SYNTAX  Gauge
	ACCESS  read-only
	STATUS mandatory
	DESCRIPTION
	" The number of Background Block Errors
	 per interval of 24 hours."
	::= { gnLptMonDayEntry 4 }

gnLptMonDayUAS OBJECT-TYPE
	SYNTAX  Gauge
	ACCESS  read-only
	STATUS mandatory
	DESCRIPTION
	" The number of Unavailable Seconds
	 per interval of 24 hours."
	::= { gnLptMonDayEntry 5 }


gnLptFarEndMonCurrTable OBJECT-TYPE
	SYNTAX  SEQUENCE OF GnLptFarEndMonCurrEntry
	ACCESS  not-accessible
	STATUS mandatory
	DESCRIPTION
	"This table maintains the counters of the far end LPT part
                of the MUX."
	::= { gnLptMon 4 }

gnLptFarEndMonCurrEntry OBJECT-TYPE
	SYNTAX GnLptFarEndMonCurrEntry
	ACCESS  not-accessible
	STATUS mandatory
	DESCRIPTION
	"This is an entry in the far end LPT part of the MUX
	 Counters Table. This table contains an interface index for every interface
	 which type is VT(51, according to RFC1573)."
	INDEX {  ifIndex }
	::= { gnLptFarEndMonCurrTable 1 }

GnLptFarEndMonCurrEntry ::=
	    SEQUENCE {
	--gnLptFarEndMonCurrES rfc1595
	--     Counter,
	--gnLptFarEndMonCurrSES
	--     Counter,
	gnLptFarEndMonCurrBBE
	     Gauge,
	gnLptFarEndMonCurrUAS
	     Gauge,
	gnLptFarEndMonCurrLastDayES
	     Gauge,
	gnLptFarEndMonCurrLastDaySES
	     Gauge,
	gnLptFarEndMonCurrLastDayBBE
	     Gauge,
	gnLptFarEndMonCurrLastDayUAS
	     Gauge
}



gnLptFarEndMonCurrBBE OBJECT-TYPE
	SYNTAX  Gauge
	ACCESS  read-only
	STATUS mandatory
	DESCRIPTION
	" The current number of Background Block Errors
	 starting  from the present 15 minutes period."
	::= { gnLptFarEndMonCurrEntry 1}

gnLptFarEndMonCurrUAS OBJECT-TYPE
	SYNTAX  Gauge
	ACCESS  read-only
	STATUS mandatory
	DESCRIPTION
	" The current number of Unavailable Seconds
	 starting  from the present 15 minutes period."
	::= { gnLptFarEndMonCurrEntry 2}


gnLptFarEndMonCurrLastDayES OBJECT-TYPE
	SYNTAX  Gauge
	ACCESS  read-only
	STATUS mandatory
	DESCRIPTION
	" The current number of Errored Seconds
	 starting  from the present 24 hours period."
	::= { gnLptFarEndMonCurrEntry 3 }

gnLptFarEndMonCurrLastDaySES OBJECT-TYPE
	SYNTAX  Gauge
	ACCESS  read-only
	STATUS mandatory
	DESCRIPTION
	" The current number of Severely Errored Seconds
	 starting 	from the present 24 hours period."
	::= { gnLptFarEndMonCurrEntry 4 }

gnLptFarEndMonCurrLastDayBBE OBJECT-TYPE
	SYNTAX  Gauge
	ACCESS  read-only
	STATUS mandatory
	DESCRIPTION
	" The current number of Background Block Errors
	 starting 	from the present 24 hours period."
	::= { gnLptFarEndMonCurrEntry 5 }

gnLptFarEndMonCurrLastDayUAS OBJECT-TYPE
	SYNTAX  Gauge
	ACCESS  read-only
	STATUS mandatory
	DESCRIPTION
	" The current number of Unavailable  Seconds
	 starting 	from the present 24 hours period."
	::= { gnLptFarEndMonCurrEntry 6 }


gnLptFarEndMonIntervalTable OBJECT-TYPE
	SYNTAX  SEQUENCE OF GnLptFarEndMonIntervalEntry
	ACCESS  not-accessible
	STATUS mandatory
	DESCRIPTION
	"This table maintains the counters of the far end LPT part
                of the MUX per interval."
	::= { gnLptMon 5 }

gnLptFarEndMonIntervalEntry OBJECT-TYPE
	SYNTAX GnLptFarEndMonIntervalEntry
	ACCESS  not-accessible
	STATUS mandatory
	DESCRIPTION
	"This is an entry in the far end LPT part of the MUX
	 Counters Table. This table contains an interface index for every interface
	 which type is VT(51, according to RFC1573).
	This table is indexed by an interval index, between 1
	to 96 and representing each one 15 minutes.
               The oldest is 96."
	INDEX {  ifIndex, gnLptFarEndMonIntervalIdx}
	::= { gnLptFarEndMonIntervalTable 1 }

GnLptFarEndMonIntervalEntry ::=
	    SEQUENCE {
	gnLptFarEndMonIntervalIdx
	      INTEGER,
	--gnLptFarEndMonIntervalES
	--     Counter,
	--gnLptFarEndMonIntervalSES
	--     Counter,
	gnLptFarEndMonIntervalBBE
	     Gauge,
	gnLptFarEndMonIntervalUAS
	     Gauge
}

gnLptFarEndMonIntervalIdx OBJECT-TYPE
	SYNTAX INTEGER (1..96)
	ACCESS read-only
	STATUS mandatory
	DESCRIPTION
	"This table is indexed per interval number. Each interval
	is of 15 minutes and the oldest is 96."
	::= { gnLptFarEndMonIntervalEntry 1 }

gnLptFarEndMonIntervalBBE OBJECT-TYPE
	SYNTAX  Gauge
	ACCESS  read-only
	STATUS mandatory
	DESCRIPTION
	" The number of Background Block Errors
	per interval."
	::= { gnLptFarEndMonIntervalEntry 2}

gnLptFarEndMonIntervalUAS OBJECT-TYPE
	SYNTAX  Gauge
	ACCESS  read-only
	STATUS mandatory
	DESCRIPTION
	" The  number of Unavailable Seconds per interval."
	::= { gnLptFarEndMonIntervalEntry 3}


gnLptFarEndMonDayTable OBJECT-TYPE
	SYNTAX  SEQUENCE OF GnLptFarEndMonDayEntry
	ACCESS  not-accessible
	STATUS mandatory
	DESCRIPTION
	"This table maintains the counters of the far end LPT part
                of the MUX per 24 hours interval."
	::= { gnLptMon 6 }

gnLptFarEndMonDayEntry OBJECT-TYPE
	SYNTAX GnLptFarEndMonDayEntry
	ACCESS  not-accessible
	STATUS mandatory
	DESCRIPTION
	"This is an entry in the far end LPT part of the MUX
	 Counters Table. This table contains an interface index for every interface
	 which type is VT(51, according to RFC1573).
	This table is indexed by an interval index, between 1
	to 30 and representing each one 24 hours.
               The oldest is 30."
	INDEX {  ifIndex, gnLptFarEndMonDayIdx}
	::= { gnLptFarEndMonDayTable 1 }

GnLptFarEndMonDayEntry ::=
	    SEQUENCE {
	gnLptFarEndMonDayIdx
	      INTEGER,
	gnLptFarEndMonDayES
	     Gauge,
	gnLptFarEndMonDaySES
	     Gauge,
	gnLptFarEndMonDayBBE
	     Gauge,
	gnLptFarEndMonDayUAS
	     Gauge
}

gnLptFarEndMonDayIdx OBJECT-TYPE
	SYNTAX INTEGER (1..30)
	ACCESS read-only
	STATUS mandatory
	DESCRIPTION
	"This table is indexed per interval number. Each interval
	is of 24 hours and the oldest is 30."
	::= { gnLptFarEndMonDayEntry 1 }

gnLptFarEndMonDayES OBJECT-TYPE
	SYNTAX  Gauge
	ACCESS  read-only
	STATUS mandatory
	DESCRIPTION
	" The number of Errored Seconds per interval of 24 hours."
	::= { gnLptFarEndMonDayEntry 2}

gnLptFarEndMonDaySES OBJECT-TYPE
	SYNTAX  Gauge
	ACCESS  read-only
	STATUS mandatory
	DESCRIPTION
	" The number of Severely Errored Seconds
	 per interval of 24 hours."
	::= { gnLptFarEndMonDayEntry 3}

gnLptFarEndMonDayBBE OBJECT-TYPE
	SYNTAX  Gauge
	ACCESS  read-only
	STATUS mandatory
	DESCRIPTION
	" The number of Background Block Errors
	 per interval of 24 hours."
	::= { gnLptFarEndMonDayEntry 4 }

gnLptFarEndMonDayUAS OBJECT-TYPE
	SYNTAX  Gauge
	ACCESS  read-only
	STATUS mandatory
	DESCRIPTION
	" The number of Unavailable Seconds
	 per interval of 24 hours."
	::= { gnLptFarEndMonDayEntry 5 }


-- /////  Protect start  ////////

gnProtect OBJECT IDENTIFIER ::=  { gnUnits 3 }


gnProtectCfgTable  OBJECT-TYPE
        SYNTAX  SEQUENCE OF GnProtectCfgEntry
        ACCESS  not-accessible
        STATUS mandatory
        DESCRIPTION
        "This table contains protection switch configuration
          per device; local and remote."
        ::= { gnProtect 1 }

gnProtectCfgEntry OBJECT-TYPE
        SYNTAX GnProtectCfgEntry
        ACCESS  not-accessible
        STATUS mandatory
        INDEX { gnProtectCfgId }
        ::= { gnProtectCfgTable 1 }

	GnProtectCfgEntry ::=
    SEQUENCE {
	gnProtectCfgId
          	INTEGER,
	gnProtectCfgSwitchRequest
	  		INTEGER,
	gnProtectCfgBERSwitch
	  		INTEGER,
	gnProtectCfgExtInSwitch
	  		INTEGER,
	gnProtectCfgOption
			OCTET STRING,
	gnProtectCfgUserCommand
	  		INTEGER
	}

gnProtectCfgId OBJECT-TYPE
	SYNTAX  INTEGER {
		local(1),
		remote(2)
	}
    ACCESS  read-only
   	STATUS mandatory
    DESCRIPTION
    " This value indicates which device is involved
	in the specific row."
        ::= { gnProtectCfgEntry 1 }


gnProtectCfgSwitchRequest OBJECT-TYPE
	SYNTAX  INTEGER {
		noAction(2),
		userSwitch(3)
	}
	ACCESS  read-write
	STATUS mandatory
	DESCRIPTION
	" Protection user switch request. "
	DEFVAL { noAction }
	::= { gnProtectCfgEntry 2 }

gnProtectCfgBERSwitch OBJECT-TYPE
	SYNTAX  INTEGER {
		enable(2),
        disable(3)
	}
	ACCESS  read-write
	STATUS mandatory
	DESCRIPTION
	" Enable or disable automatic switch as a result of BER condition. "
	DEFVAL { enable }
	::= { gnProtectCfgEntry 3 }

gnProtectCfgExtInSwitch OBJECT-TYPE
	SYNTAX  INTEGER {
		enable(2),
        disable(3)
	}
	ACCESS  read-write
	STATUS mandatory
	DESCRIPTION
	" Enable or disable automatic switch as a result of alarm
	  on External Input No. 8. "
	DEFVAL { enable }
	::= { gnProtectCfgEntry 4 }


gnProtectCfgOption OBJECT-TYPE
	SYNTAX  OCTET STRING (SIZE(1))
	ACCESS  read-write
	STATUS mandatory
	DESCRIPTION
	" bit 7 	  = protection disable
	  bit 8 (lsb) = dual fiber input. "
	::= { gnProtectCfgEntry 5 }

gnProtectCfgUserCommand OBJECT-TYPE
	SYNTAX  INTEGER {
		noAction(2),
		copyConfToMate(3)
	}
	ACCESS  read-write
	STATUS mandatory
	DESCRIPTION
	" Copy All the configuration that should be equal in master and slave.
	  The copy is made from the current unit to it's mate."
	DEFVAL { noAction }
	::= { gnProtectCfgEntry 6 }


gnProtectUnitMode OBJECT-TYPE
	SYNTAX  INTEGER {
		slave(2),
		master(3)
	}
	ACCESS  read-only
	STATUS mandatory
	DESCRIPTION
	" This parameter indicates the unit mode: Master of Slave."
	DEFVAL { slave }
	::= { gnProtect 2 }


gnHitLessCfgTable  OBJECT-TYPE
        SYNTAX  SEQUENCE OF GnHitLessCfgEntry
        ACCESS  not-accessible
        STATUS mandatory
        DESCRIPTION
        "This table contains hitless configuration
          per device; local and remote."
        ::= { gnProtect 3 }

gnHitLessCfgEntry OBJECT-TYPE
        SYNTAX GnHitLessCfgEntry
        ACCESS  not-accessible
        STATUS mandatory
        INDEX { gnHitLessCfgId }
        ::= { gnHitLessCfgTable 1 }

	GnHitLessCfgEntry ::=
    SEQUENCE {
	gnHitLessCfgId
			INTEGER,
	gnHitLessCfgSwitchEnable
          	INTEGER,
	gnHitLessCfgDiversityType
	  		INTEGER,
	gnHitLessCfgSwitchingMode
	  		INTEGER,
	gnHitLessCfgRevertTime
	  		INTEGER,
	gnHitLessCfgManualSwitch
	  		INTEGER,
	gnHitLessCfgEventCounterCommand
			INTEGER
	}

gnHitLessCfgId OBJECT-TYPE
	SYNTAX  INTEGER {
		local(1),
		remote(2)
	}
    ACCESS  read-only
   	STATUS mandatory
    DESCRIPTION
    " This value indicates which device is involved
	in the specific row."
        ::= { gnHitLessCfgEntry 1 }

gnHitLessCfgSwitchEnable OBJECT-TYPE
	SYNTAX  INTEGER {
		enable(2),
        disable(3)
	}
	ACCESS  read-write
   	STATUS mandatory
    DESCRIPTION
    " Enable or disable the Hitless feature."
	DEFVAL { enable }
        ::= { gnHitLessCfgEntry 2 }

gnHitLessCfgDiversityType OBJECT-TYPE
	SYNTAX  INTEGER {
		space(2),
        frequency(3)
	}
	ACCESS  read-write
   	STATUS mandatory
    DESCRIPTION
    " Is the hitless feature working in space diversity mode 
	or in frequency diversity mode."
	DEFVAL { space }
        ::= { gnHitLessCfgEntry 3 }

gnHitLessCfgSwitchingMode OBJECT-TYPE
	SYNTAX  INTEGER {
		revertive(2),
        nonRevertive(3)
	}
	ACCESS  read-write
   	STATUS mandatory
    DESCRIPTION
    " "
	DEFVAL { revertive }
        ::= { gnHitLessCfgEntry 4 }

gnHitLessCfgRevertTime OBJECT-TYPE
	SYNTAX  INTEGER (0..15)
	ACCESS  read-write
   	STATUS mandatory
    DESCRIPTION
    " This parameter indicates the revert time in seconds.
	Possible values: 0..15."
	DEFVAL { 0 }
        ::= { gnHitLessCfgEntry 5 }

gnHitLessCfgManualSwitch OBJECT-TYPE
	SYNTAX  INTEGER {
		noAction(2),
        activate(3)
	}
	ACCESS  read-write
   	STATUS mandatory
    DESCRIPTION
    " Force manually switch between the hitless modems."
	DEFVAL { noAction }
        ::= { gnHitLessCfgEntry 6 }

gnHitLessCfgEventCounterCommand OBJECT-TYPE
	SYNTAX  INTEGER {
		noAction(2),
        clearCounter(3)
	}
	ACCESS  read-write
   	STATUS mandatory
    DESCRIPTION
    " Clears the gnHitLessStatEventCounter."
	DEFVAL { noAction }
        ::= { gnHitLessCfgEntry 7 }


gnHitLessStatTable  OBJECT-TYPE
        SYNTAX  SEQUENCE OF GnHitLessStatEntry
        ACCESS  not-accessible
        STATUS mandatory
        DESCRIPTION
        "This table contains hitless status
          per device; local and remote."
        ::= { gnProtect 4 }

gnHitLessStatEntry OBJECT-TYPE
        SYNTAX GnHitLessStatEntry
        ACCESS  not-accessible
        STATUS mandatory
        INDEX { gnHitLessStatId }
        ::= { gnHitLessStatTable 1 }

	GnHitLessStatEntry ::=
    SEQUENCE {
	gnHitLessStatId
			INTEGER,
	gnHitLessStatReceiverStatus
          	INTEGER,
	gnHitLessStatModeStatus
	  		INTEGER,
	gnHitLessStatEventCounter
	  		INTEGER,
	gnHitLessStatAlarmStatus
			OCTET STRING
	}

gnHitLessStatId OBJECT-TYPE
	SYNTAX  INTEGER {
		local(1),
		remote(2)
	}
    ACCESS  read-only
   	STATUS mandatory
    DESCRIPTION
    " This value indicates which device is involved
	in the specific row."
        ::= { gnHitLessStatEntry 1 }

gnHitLessStatReceiverStatus OBJECT-TYPE
	SYNTAX  INTEGER {
		local(2),
        mate(3)
	}
	ACCESS  read-only
   	STATUS mandatory
    DESCRIPTION
    " This parameter indicates which Modem is active:
	the Local or the mate."
	DEFVAL { local }
        ::= { gnHitLessStatEntry 2 }

gnHitLessStatModeStatus OBJECT-TYPE
	SYNTAX  INTEGER {
		hitlessOK(2),
        hitlessFailure(3)
	}
	ACCESS  read-only
   	STATUS mandatory
    DESCRIPTION
    " This parameter indicates if the Hitless system 
	is working properly."
	DEFVAL { hitlessFailure }
        ::= { gnHitLessStatEntry 3 }

gnHitLessStatEventCounter OBJECT-TYPE
	SYNTAX  INTEGER (0..65535)
	ACCESS  read-only
   	STATUS mandatory
    DESCRIPTION
    " This counter counts the number of hitless switch events."
	DEFVAL { 0 }
        ::= { gnHitLessStatEntry 4 }

gnHitLessStatAlarmStatus OBJECT-TYPE
	SYNTAX  OCTET STRING (SIZE(2))
	ACCESS  read-only
   	STATUS mandatory
    DESCRIPTION
    " bit 1 represent the MSB
	bits 1-12: are not in use
	bit 13: Hitless Functionality Failure.
	bit 14:	Hitless Cable Disconnect.
	bit 15: Hitless Mate LOF.
	bit 16: Hitless Primary Radio LOF. "
        ::= { gnHitLessStatEntry 5 }


gnTribStmProtectCfg OBJECT IDENTIFIER ::= { gnProtect 5}

gnTribStmProtectType OBJECT-TYPE
	SYNTAX  INTEGER {
		none(2),
		msp(3),
		sncp(4)
	}
	ACCESS  read-write
	STATUS mandatory
	DESCRIPTION
	"."
	DEFVAL { none }
	::= { gnTribStmProtectCfg 1 }

gnTribStmMspConnect OBJECT-TYPE
	SYNTAX  INTEGER {
		dualTribConnect(2),
		singleTribConnect(3)
	}
	ACCESS  read-write
	STATUS mandatory
	DESCRIPTION
	"."
	DEFVAL { dualTribConnect }
	::= { gnTribStmProtectCfg 2 }

gnTribStmMspType OBJECT-TYPE
	SYNTAX  INTEGER {
		uniDirectional(2),
		biDirectional(3)
	}
	ACCESS  read-write
	STATUS mandatory
	DESCRIPTION
	"."
	DEFVAL { uniDirectional }
	::= { gnTribStmProtectCfg 3 }

gnTribStmMspRevertiveMode OBJECT-TYPE
	SYNTAX  INTEGER {
		nonRevertive(2),
		revertive(3)
	}
	ACCESS  read-write
	STATUS mandatory
	DESCRIPTION
	"."
	DEFVAL { nonRevertive }
	::= { gnTribStmProtectCfg 4 }

gnTribStmMspProtectRole OBJECT-TYPE
	SYNTAX  INTEGER {
		main(2),
		standBy(3)
	}
	ACCESS  read-write
	STATUS mandatory
	DESCRIPTION
	"."
	::= { gnTribStmProtectCfg 5 }

gnTribStmMspWaitToRestoreTime OBJECT-TYPE
	SYNTAX  INTEGER (5..12)
	ACCESS  read-write
	STATUS mandatory
	DESCRIPTION
  	"This is the wait-to-restore time in minutes.
	 Possible values: 5..12. "
	DEFVAL {5}
	::= { gnTribStmProtectCfg 6 }

gnTribStmMspUserCommand OBJECT-TYPE
	SYNTAX  INTEGER {
				clear(2),
                lockOut(3),
                forceSwitch(4),
                manualSwitch(5),
				exercise(6)
        }
	ACCESS  read-write
	STATUS mandatory
	DESCRIPTION
	"."
	DEFVAL { clear }
	::= { gnTribStmProtectCfg 7 }



gnTribStmProtectStat OBJECT IDENTIFIER ::= { gnProtect 6}

gnTribStmProtectCurrentState OBJECT-TYPE
	SYNTAX  INTEGER {
		working(2),
		protecting(3)
	}
	ACCESS  read-only
	STATUS mandatory
	DESCRIPTION
	"."
	::= { gnTribStmProtectStat 1 }

gnTribStmProtectCableStatus OBJECT-TYPE
	SYNTAX  INTEGER {
		ok(2),
		fault(3)
	}
	ACCESS  read-only
	STATUS mandatory
	DESCRIPTION
	"."
	::= { gnTribStmProtectStat 2 }


-- /////  Protect end  ////////////

gnSSM OBJECT IDENTIFIER ::=  { gnUnits 4 }

gnSSMCfg OBJECT IDENTIFIER ::=  { gnSSM 1 }

gnSSMCfgSSMMode OBJECT-TYPE
	SYNTAX  INTEGER { 
	enabled(2), 
	disabled(3)
	}
	ACCESS  read-write
	STATUS mandatory
	DESCRIPTION
	" "
	DEFVAL { disabled }
	::= { gnSSMCfg  1 }

gnSSMCfgPrimaryClockSource OBJECT-TYPE
	SYNTAX  INTEGER {
				internalClock(2),
                external2MB(3),
                radioClock(4),
                fiberClock(5),
                external2MHz(6),
                external1AndHalfMB(7),
				tributaryClock1(8),
				tributaryClock2(9),
				tributaryClock3(10),
				tributaryClock4(11),
				tributaryClock5(12),
				tributaryClock6(13),
				tributaryClock7(14),
				tributaryClock8(15),
				tributaryClock9(16),
				tributaryClock10(17),
				tributaryClock11(18),
				tributaryClock12(19),
				tributaryClock13(20),
				tributaryClock14(21),
				tributaryClock15(22),
				tributaryClock16(23),
				tribSTM1(24)
	}
	ACCESS  read-write
	STATUS mandatory
	DESCRIPTION
	"The primary clock source, configurable for ACCESS radios only."
        DEFVAL { internalClock }
	::= { gnSSMCfg 2 }

gnSSMCfgPrimaryClockQuality OBJECT-TYPE
	SYNTAX  INTEGER (1..6)
	ACCESS  read-write
	STATUS mandatory
	DESCRIPTION
	" This parameter indicates the primary clock quality.
	Possible values for SDH:
	PRC(1), SSUT(2), SSUL(3), SEC(4), STU(5).
	Possible values for Sonet:
	PRS(1), STU(2), ST2(3), ST3(4), SMC(5), ST4(6).	"
	::= { gnSSMCfg  3 }

gnSSMCfgSecondaryClockSource OBJECT-TYPE
	SYNTAX  INTEGER {
				internalClock(2),
                external2MB(3),
                radioClock(4),
                fiberClock(5),
                external2MHz(6),
                external1AndHalfMB(7),
				tributaryClock1(8),
				tributaryClock2(9),
				tributaryClock3(10),
				tributaryClock4(11),
				tributaryClock5(12),
				tributaryClock6(13),
				tributaryClock7(14),
				tributaryClock8(15),
				tributaryClock9(16),
				tributaryClock10(17),
				tributaryClock11(18),
				tributaryClock12(19),
				tributaryClock13(20),
				tributaryClock14(21),
				tributaryClock15(22),
				tributaryClock16(23),
				tribSTM1(24)
        }
	ACCESS  read-write
	STATUS mandatory
	DESCRIPTION
	"The secondary clock source, configurable for ACCESS radios only."
        DEFVAL { internalClock }
	::= { gnSSMCfg 4 }

gnSSMCfgSecondaryClockQuality OBJECT-TYPE
	SYNTAX  INTEGER (1..6)
	ACCESS  read-write
	STATUS mandatory
	DESCRIPTION
	" This parameter indicates the secondary clock quality.
	Possible values for SDH:
	PRC(1), SSUT(2), SSUL(3), SEC(4), STU(5).
	Possible values for Sonet:
	PRS(1), STU(2), ST2(3), ST3(4), SMC(5), ST4(6).	"
	::= { gnSSMCfg  5 }

gnSSMCfgClockUserCommand OBJECT-TYPE
	SYNTAX  INTEGER {
				noAction(2),
                switchToPrimaryClock(3),
                switchToSecondaryClock(4),
                switchToInternalClock(5)
        }
	ACCESS  read-write
	STATUS mandatory
	DESCRIPTION
	"The clock user command.
	 Switch is possible only when the SSM mode is disable."
        DEFVAL { noAction }
	::= { gnSSMCfg 6 }

gnSSMCfgClockOutputMute OBJECT-TYPE
	SYNTAX  INTEGER { on(2), off(3) }
	ACCESS  read-write
	STATUS mandatory
	DESCRIPTION
	"This parameter indicates if clock output will be in mute state.
            (Mute on -> don't transmit) "
	DEFVAL { 2 }
	::= { gnSSMCfg 7 }


gnSSMStat OBJECT IDENTIFIER ::=  { gnSSM 2 }

gnSSMStatStatus OBJECT-TYPE
	SYNTAX OCTET STRING(SIZE(2))
	ACCESS  read-only
	STATUS mandatory
	DESCRIPTION
	" Alarm status of SSM. Bit 1 is MSB, bit=1 when alarm active.
	  bit 1 = Unlock
	  bit 2 = Out Of Range
	  bit 3 = Primary Clock Source Failure
	  bit 4 = Secondary Clock Source Failure "
	::= { gnSSMStat  1 }

gnSSMStatCurrentClock OBJECT-TYPE
	SYNTAX INTEGER {
		primary(2),
		secondary(3),
		internal(4),
		holdOver(5)
	}
	ACCESS  read-only
	STATUS mandatory
	DESCRIPTION
	" "
	::= { gnSSMStat  2 }

gnSSMStatCurrentClockQuality OBJECT-TYPE
	SYNTAX  INTEGER (1..7)
	ACCESS  read-only
	STATUS mandatory
	DESCRIPTION
	" This parameter indicates the current clock quality.
	SDH values: PRC(1), SSUT(2), SSUL(3), SEC(4), STU(5), DNU(6).
	Sonet values: PRS(1), STU(2), ST2(3), ST3(4), SMC(5), ST4(6), DUS(7)."
	::= { gnSSMStat  3 }

gnSSMStatClockUnitType OBJECT-TYPE
	SYNTAX INTEGER {
		noClockUnit(2),
		smc(3),
		sec(4),
		st3(5),
		st3e(6)
	}
	ACCESS  read-only
	STATUS mandatory
	DESCRIPTION
	"  "
	::= { gnSSMStat  4 }

gnSSMStatHoldoverPeriod OBJECT-TYPE
	SYNTAX INTEGER (0..2880)
	ACCESS  read-only
	STATUS mandatory
	DESCRIPTION
	"This parameter indicates the minutes time period in holdover state. "
	DEFVAL { 0 }
	::= { gnSSMStat  5 }


gnAccess OBJECT IDENTIFIER ::= { ceragon 4 }
gnAccessCfg OBJECT IDENTIFIER ::= { gnAccess 1 }
gnAccessCfgTable OBJECT-TYPE
	SYNTAX  SEQUENCE OF GnAccessCfgEntry
	ACCESS  not-accessible
	STATUS mandatory
	DESCRIPTION
	"This table defines the configuration and status of the access ports."
	::= { gnAccessCfg 1 }

gnAccessCfgEntry OBJECT-TYPE
	SYNTAX GnAccessCfgEntry
	ACCESS  not-accessible
	STATUS mandatory
	DESCRIPTION
	"Entry for the table containing an interface index for every interface
	 which type is DS3 (30, according to RFC1573)."
	INDEX {  ifIndex }
	::= { gnAccessCfgTable 1 }

GnAccessCfgEntry ::=
	    SEQUENCE {
	gnAccessCfgLongCableOption
	     INTEGER,
	gnAccessCfgLoopbackOption
	     INTEGER,
	gnAccessCfgRunPrbs
	     INTEGER,
	gnAccessCfgEXCThresh
		INTEGER,
	gnAccessCfgSDThresh
		INTEGER,
	gnAccessCfgTest
		INTEGER,
	gnAccessCfgLineCoding
		INTEGER
}


gnAccessCfgLongCableOption OBJECT-TYPE
	SYNTAX  INTEGER { 
	ds3ShortCable(2), 
	ds3LongCable(3),
	t1From0to133ft(4),
	t1From133to266ft(5),
	t1From266to399ft(6), 
	t1From399to533ft(7),
	t1From533to655ft(8),
	anyLength(9)
	}
	ACCESS  read-write
	STATUS mandatory
	DESCRIPTION
	" This parameter defines the line build-out option.
	Possible values:
	For DS3: ds3ShortCable, ds3LongCable.
	For T1: t1From0to133ft..t1From533to655ft.
	For E1/E3: anyLength. "
	DEFVAL { t1From0to133ft }
	::= { gnAccessCfgEntry  1 }

gnAccessCfgLoopbackOption OBJECT-TYPE
	SYNTAX  INTEGER {
		noloopback(2),
		interfaceInterLoop(3),
		interfaceExterLoop(4)
		}
	ACCESS  read-write
	STATUS mandatory
	DESCRIPTION
	" This parameter enable the user to launch a loopback."
	::= { gnAccessCfgEntry  2 }

gnAccessCfgRunPrbs OBJECT-TYPE
	SYNTAX  INTEGER {
		noOperation(2),
		lineOnRadioOnRcvLine(3),
		lineOnRadioOnRcvRadio(4),
		lineOnRadioOffRcvLine(5),
		lineOnRadioOffRcvRadio(6),
		lineOffRadioOnRcvLine(7),
		lineOffRadioOnRcvRadio(8),
		lineOffRadioOffRcvLine(9),
		lineOffRadioOffRcvRadio(10),
		lineOnRadioOnRcvOff(11),
		lineOffRadioOnRcvOff(12),
		lineOnRadioOffRcvOff(13)
		}

	ACCESS  read-write
	STATUS mandatory
	DESCRIPTION
	"This parameter enables launching a PRBS test."
	::= { gnAccessCfgEntry  3 }

gnAccessCfgEXCThresh OBJECT-TYPE
	SYNTAX  INTEGER {
			tenExpMinus3(2),
			tenExpMinus4(3),
			tenExpMinus5(4)
	}
	ACCESS  read-write
	STATUS mandatory
	DESCRIPTION
	" If the bit error rate is higher than this threshold
	 an EXC alarm would be generated.
	EXC is for excessive."
	DEFVAL { tenExpMinus3}
	::= { gnAccessCfgEntry 4 }

gnAccessCfgSDThresh OBJECT-TYPE
	SYNTAX  INTEGER {
			tenExpMinus6(3),
			tenExpMinus7(4),
			tenExpMinus8(5),
			tenExpMinus9(6)
	}
	ACCESS  read-write
	STATUS mandatory
	DESCRIPTION
	" If the bit error rate is higher than this threshold
	 a SD alarm would be generated.
	SD is for Signal Degrade."
	DEFVAL { tenExpMinus6}
	::= { gnAccessCfgEntry 5 }

gnAccessCfgTest OBJECT-TYPE
	SYNTAX  INTEGER {
			noAction(2),
			sendAIS(3)
	}
	ACCESS  read-write
	STATUS mandatory
	DESCRIPTION
	"This parameter controls the action to send AIS or not."
	::= { gnAccessCfgEntry 6 }

gnAccessCfgLineCoding OBJECT-TYPE
	SYNTAX  INTEGER {
			ami(2),
			b8zs(3),
			hdb3(4),
			b3zs(5)
	}
	ACCESS  read-write
	STATUS mandatory
	DESCRIPTION
	"The line coding possible values:
	 For T1: B7ZS(ami), B8ZS.
	 For E1 & E3: HDB3.
	 For DS3: B3ZS"
	::= { gnAccessCfgEntry 7 }

---------------
gnAccessStat OBJECT IDENTIFIER ::= { gnAccess 2 }
gnAccessStatTable OBJECT-TYPE
	SYNTAX  SEQUENCE OF GnAccessStatEntry
	ACCESS  not-accessible
	STATUS mandatory
	DESCRIPTION
	"This table defines the status of the access ports."
	::= { gnAccessStat 1 }

gnAccessStatEntry OBJECT-TYPE
	SYNTAX GnAccessStatEntry
	ACCESS  not-accessible
	STATUS mandatory
	DESCRIPTION
	"Entry for the table containing an interface index for every interface
	 which type is DS3 (30, according to RFC1573)."
	INDEX {  ifIndex }
	::= { gnAccessStatTable 1 }

GnAccessStatEntry ::=
	    SEQUENCE {
	gnAccessStatInterfaceBer
	   INTEGER,
	gnAccessStatStatus
	   OCTET STRING,
	gnAccessStatPrbsBer
	   INTEGER
}
gnAccessStatInterfaceBer OBJECT-TYPE
	SYNTAX  INTEGER {
			tenExpMinus3(2),
			tenExpMinus4(3),
			tenExpMinus5(4),
			tenExpMinus6(5),
			tenExpMinus7(6),
			tenExpMinus8(7),
			tenExpMinus9(8),
			tenExpMinus10(9),
			tenExpMinus11(10),
			tenExpMinus12(11),
			tenExpMinus13(12),
			tenExpMinus14(13)
	}
	ACCESS  read-only
	STATUS mandatory
	DESCRIPTION
	" Current Bit Error Rate. "
	::= { gnAccessStatEntry  1 }

gnAccessStatStatus OBJECT-TYPE
	SYNTAX OCTET STRING(SIZE(2))
	ACCESS  read-only
	STATUS mandatory
	DESCRIPTION
	" Alarm status of an ACCESS radio. Bit 1 is MSB, bit=1 when alarm active.
	  bit 2  = LOS
	  bit 6  = AIS
	  bit 9  = SD
	  bit 10 = EXC
	  bit 11 = Unexpected signal -- when disabled, will rise if detect data.
	  bit 14 = Out Of Lock "
	::= { gnAccessStatEntry 2 }

gnAccessStatPrbsBer OBJECT-TYPE
	SYNTAX  INTEGER {
			tenExpMinus3(2),
			tenExpMinus4(3),
			tenExpMinus5(4),
			tenExpMinus6(5),
			tenExpMinus7(6),
			tenExpMinus8(7),
			tenExpMinus9(8),
			tenExpMinus10(9),
			tenExpMinus11(10),
			tenExpMinus12(11),
			tenExpMinus13(12),
			tenExpMinus14(13)
	}
	ACCESS  read-only
	STATUS mandatory
	DESCRIPTION
	"Current PRBS Errors of the operation set
	in the mib variable gnAccessCfgRunPrbs,
	use this variable to clear the error counter."
	::= { gnAccessStatEntry  3 }



----
gnFastEthernetCfg OBJECT IDENTIFIER ::= { gnAccess 3 }
gnFastEthernetCfgTable OBJECT-TYPE
	SYNTAX  SEQUENCE OF GnFastEthernetCfgEntry
	ACCESS  not-accessible
	STATUS mandatory
	DESCRIPTION
	"This table defines the configuration of the Fast Ethernet ports."
	::= { gnFastEthernetCfg 1 }

gnFastEthernetCfgEntry OBJECT-TYPE
	SYNTAX GnFastEthernetCfgEntry
	ACCESS  not-accessible
	STATUS mandatory
	DESCRIPTION
	"This is an entry in the Fast Ethernet configuration table."
	INDEX {  ifIndex }
	::= { gnFastEthernetCfgTable 1 }

GnFastEthernetCfgEntry ::=
	    SEQUENCE {
	gnFastEthernetCfgAutoNegotiation		
	     INTEGER,
	gnFastEthernetCfgForceSpeed
	     INTEGER,
	gnFastEthernetCfgDynamicBand
		INTEGER,
	gnFastEthernetCfgGigabitEthernet
		INTEGER
}

gnFastEthernetCfgAutoNegotiation OBJECT-TYPE
	SYNTAX  INTEGER { on(2), off(3) }
	ACCESS  read-write
	STATUS mandatory
	DESCRIPTION
	" This parameter defines if auto negotiations protocol is active."
	::= { gnFastEthernetCfgEntry  1 }

gnFastEthernetCfgForceSpeed OBJECT-TYPE
	SYNTAX  INTEGER {
		tenBased(2),
		hundredBased(3)
		}
	ACCESS  read-write
	STATUS mandatory
	DESCRIPTION
	"This parameter force speed when auto negotiation is off."
	::= { gnFastEthernetCfgEntry  2 }

gnFastEthernetCfgDynamicBand OBJECT-TYPE
	SYNTAX  INTEGER {
			notActive(2),
			dynamic(3),
			leftPreferred(4)
	}
	ACCESS  read-write
	STATUS mandatory
	DESCRIPTION										   
	"Dynamic bandwidth allocation:
	dynamic means that the two Fast Ethernet ports have the same priority. 
	LeftPreferred indicates that left Fast Ethernet card priority is higher."
	::= { gnFastEthernetCfgEntry 3 }

gnFastEthernetCfgGigabitEthernet OBJECT-TYPE
	SYNTAX  INTEGER {
			disable(2),
			enable(3)
	}
	ACCESS  read-write
	STATUS mandatory
	DESCRIPTION										   
	" Gigabit Ethernet option.
	This parameter will be changed after reset. "
	::= { gnFastEthernetCfgEntry 4 }

----
gnFastEthernetStat OBJECT IDENTIFIER ::= { gnAccess 4 }
gnFastEthernetStatTable OBJECT-TYPE
	SYNTAX  SEQUENCE OF GnFastEthernetStatEntry
	ACCESS  not-accessible
	STATUS mandatory
	DESCRIPTION
	"The Fast Ethernet status table."
	::= { gnFastEthernetStat 1 }

gnFastEthernetStatEntry OBJECT-TYPE
	SYNTAX GnFastEthernetStatEntry
	ACCESS  not-accessible
	STATUS mandatory
	DESCRIPTION
	"This is an entry in the Fast Ethernet status table."
	INDEX {  ifIndex }
	::= { gnFastEthernetStatTable 1 }

GnFastEthernetStatEntry ::=
	    SEQUENCE {
	gnFastEthernetStatStatus
	   OCTET STRING
}

gnFastEthernetStatStatus OBJECT-TYPE
	SYNTAX OCTET STRING(SIZE(2))
	ACCESS  read-only
	STATUS mandatory
	DESCRIPTION
	" Alarm status of an FE radio. Bit 1 is MSB, bit=1 when alarm active. 
	  bit 2 = Loss of Carrier"
	::= { gnFastEthernetStatEntry 1 }

----
-- Statistics(PM) For PDH (NB DS3). All PDH tables are included for future 
-- development and are not currently implemented.
gnPdhMon OBJECT IDENTIFIER ::=  { gnAccess 5 }

gnPdhMonCurrTable OBJECT-TYPE
	SYNTAX  SEQUENCE OF GnPdhMonCurrEntry
	ACCESS  not-accessible
	STATUS mandatory
	DESCRIPTION
	"This table maintains the counters for the PDH table. "
	::= { gnPdhMon 1 }

gnPdhMonCurrEntry OBJECT-TYPE
	SYNTAX GnPdhMonCurrEntry
	ACCESS  not-accessible
	STATUS mandatory
	DESCRIPTION
	"This is an entry in the PDH
	 Counters Table. This table contains an interface index for every interface
	 which type is DS3(30, according to RFC1573)."
	INDEX {  ifIndex }
	::= { gnPdhMonCurrTable 1 }

GnPdhMonCurrEntry ::=
	    SEQUENCE {
	gnPdhMonCurrES 
	     Gauge,
	gnPdhMonCurrSES
	     Gauge,
	gnPdhMonCurrBBE
	     Gauge,
	gnPdhMonCurrUAS
	     Gauge,
	gnPdhMonCurrCV
	     Gauge,
	gnPdhMonCurrLastDayES
	     Gauge,
	gnPdhMonCurrLastDaySES
	     Gauge,
	gnPdhMonCurrLastDayBBE
	     Gauge,
	gnPdhMonCurrLastDayUAS
	     Gauge,
	gnPdhMonCurrLastDayCV
	     Gauge
}

gnPdhMonCurrES OBJECT-TYPE
	SYNTAX  Gauge
	ACCESS  read-only
	STATUS mandatory
	DESCRIPTION
	"The current number of errored seconds starting from the present 15 minute 
period.  ."
	::= { gnPdhMonCurrEntry 1}

gnPdhMonCurrSES OBJECT-TYPE
	SYNTAX  Gauge
	ACCESS  read-only
	STATUS mandatory
	DESCRIPTION
	"The current number of severely errored seconds, starting from the present 
15 minute period."
	::= { gnPdhMonCurrEntry 2}


gnPdhMonCurrBBE OBJECT-TYPE
	SYNTAX  Gauge
	ACCESS  read-only
	STATUS mandatory
	DESCRIPTION
	" The current number of Background Block Errors
	 starting from the present 15 minutes period."
	::= { gnPdhMonCurrEntry 3}

gnPdhMonCurrUAS OBJECT-TYPE
	SYNTAX  Gauge
	ACCESS  read-only
	STATUS mandatory
	DESCRIPTION
	" The current number of Unavailable Seconds
	 starting 	from the present 15 minutes period."
	::= { gnPdhMonCurrEntry 4}

gnPdhMonCurrCV OBJECT-TYPE
	SYNTAX  Gauge
	ACCESS  read-only
	STATUS mandatory
	DESCRIPTION
	" The current number of CV
	 starting from the present 15 minutes period."
	::= { gnPdhMonCurrEntry 5}

gnPdhMonCurrLastDayES OBJECT-TYPE
	SYNTAX  Gauge
	ACCESS  read-only
	STATUS mandatory
	DESCRIPTION
	" The current number of Errored Seconds
	 starting from the present 24 hours period."
	::= { gnPdhMonCurrEntry 6 }

gnPdhMonCurrLastDaySES OBJECT-TYPE
	SYNTAX  Gauge
	ACCESS  read-only
	STATUS mandatory
	DESCRIPTION
	" The current number of Severely Errored Seconds
	 starting from the present 24 hours period."
	::= { gnPdhMonCurrEntry 7 }

gnPdhMonCurrLastDayBBE OBJECT-TYPE
	SYNTAX  Gauge
	ACCESS  read-only
	STATUS mandatory
	DESCRIPTION
	" The current number of Background Block Errors
	 starting 	from the present 24 hours period."
	::= { gnPdhMonCurrEntry 8 }

gnPdhMonCurrLastDayUAS OBJECT-TYPE
	SYNTAX  Gauge
	ACCESS  read-only
	STATUS mandatory
	DESCRIPTION
	" The current number of Unavailable  Seconds
	 starting 	from the present 24 hours period."
	::= { gnPdhMonCurrEntry 9 }

gnPdhMonCurrLastDayCV OBJECT-TYPE
	SYNTAX  Gauge
	ACCESS  read-only
	STATUS mandatory
	DESCRIPTION
	"The current number of CV, starting from the present 24-hour period."
	::= { gnPdhMonCurrEntry 10}



gnPdhMonIntervalTable OBJECT-TYPE
	SYNTAX  SEQUENCE OF GnPdhMonIntervalEntry
	ACCESS  not-accessible
	STATUS mandatory
	DESCRIPTION
	"This table maintains the counters of the PDH per interval."
	::= { gnPdhMon 2 }


gnPdhMonIntervalEntry OBJECT-TYPE
	SYNTAX GnPdhMonIntervalEntry
	ACCESS  not-accessible
	STATUS mandatory
	DESCRIPTION
	"This is an entry in the PDH
	 Counters Table. This table contains an interface index for every interface
	 which type is DS3(30, according to RFC1573).
	This table is indexed by an interval index, between 1
	to 96 and representing each one 15 minutes.
               The oldest is 96."
	INDEX {  ifIndex, gnPdhMonIntervalIdx}
	::= { gnPdhMonIntervalTable 1 }

GnPdhMonIntervalEntry ::=
	    SEQUENCE {
	gnPdhMonIntervalIdx
	      INTEGER,
	gnPdhMonIntervalES
	     Gauge,
	gnPdhMonIntervalSES
	     Gauge,
	gnPdhMonIntervalBBE
	     Gauge,
	gnPdhMonIntervalUAS
	     Gauge,
	gnPdhMonIntervalCV
	     Gauge
}

gnPdhMonIntervalIdx OBJECT-TYPE
	SYNTAX INTEGER (1..96)
	ACCESS read-only
	STATUS mandatory
	DESCRIPTION
	"This table is indexed per interval number. Each interval
	is of 15 minutes and the oldest is 96."
	::= { gnPdhMonIntervalEntry 1 }

gnPdhMonIntervalES OBJECT-TYPE
	SYNTAX  Gauge
	ACCESS  read-only
	STATUS mandatory
	DESCRIPTION
	"The number of errored seconds per interval."
	::= { gnPdhMonIntervalEntry 2}

gnPdhMonIntervalSES OBJECT-TYPE
	SYNTAX  Gauge
	ACCESS  read-only
	STATUS mandatory
	DESCRIPTION
	"The number of severely errored seconds per interval."
	::= { gnPdhMonIntervalEntry 3}

gnPdhMonIntervalBBE OBJECT-TYPE
	SYNTAX  Gauge
	ACCESS  read-only
	STATUS mandatory
	DESCRIPTION
	" The number of Background Block Errors
	per interval."
	::= { gnPdhMonIntervalEntry 4}

gnPdhMonIntervalUAS OBJECT-TYPE
	SYNTAX  Gauge
	ACCESS  read-only
	STATUS mandatory
	DESCRIPTION
	" The  number of Unavailable Seconds per interval."
	::= { gnPdhMonIntervalEntry 5}

gnPdhMonIntervalCV OBJECT-TYPE
	SYNTAX  Gauge
	ACCESS  read-only
	STATUS mandatory
	DESCRIPTION
	"The number of CV per interval."
	::= { gnPdhMonIntervalEntry 6}


gnPdhMonDayTable OBJECT-TYPE
	SYNTAX  SEQUENCE OF GnPdhMonDayEntry
	ACCESS  not-accessible
	STATUS mandatory
	DESCRIPTION
	"This table maintains the counters of the PDH per 24 hours interval."
	::= { gnPdhMon 3 }

gnPdhMonDayEntry OBJECT-TYPE
	SYNTAX GnPdhMonDayEntry
	ACCESS  not-accessible
	STATUS mandatory
	DESCRIPTION
	"This is an entry in the PDH
	 Counters Table. This table contains an interface index for every interface
	 which type is DS3(30, according to RFC1573).
	This table is indexed by an interval index, between 1
	to 30 and representing each one 24 hours.
               The oldest is 30."
	INDEX {  ifIndex, gnPdhMonDayIdx}
	::= { gnPdhMonDayTable 1 }

GnPdhMonDayEntry ::=
	    SEQUENCE {
	gnPdhMonDayIdx
	      INTEGER,
	gnPdhMonDayES
	     Gauge,
	gnPdhMonDaySES
	     Gauge,
	gnPdhMonDayBBE
	     Gauge,
	gnPdhMonDayUAS
	     Gauge,
	gnPdhMonDayCV
	     Gauge
}

gnPdhMonDayIdx OBJECT-TYPE
	SYNTAX INTEGER (1..30)
	ACCESS read-only
	STATUS mandatory
	DESCRIPTION
	"This table is indexed per interval number. Each interval
	is of 24 hours and the oldest is 30."
	::= { gnPdhMonDayEntry 1 }

gnPdhMonDayES OBJECT-TYPE
	SYNTAX  Gauge
	ACCESS  read-only
	STATUS mandatory
	DESCRIPTION
	" The number of Errored Seconds per interval of 24 hours."
	::= { gnPdhMonDayEntry 2}

gnPdhMonDaySES OBJECT-TYPE
	SYNTAX  Gauge
	ACCESS  read-only
	STATUS mandatory
	DESCRIPTION
	" The number of Severely Errored Seconds
	 per interval of 24 hours."
	::= { gnPdhMonDayEntry 3}

gnPdhMonDayBBE OBJECT-TYPE
	SYNTAX  Gauge
	ACCESS  read-only
	STATUS mandatory
	DESCRIPTION
	" The number of Background Block Errors
	 per interval of 24 hours."
	::= { gnPdhMonDayEntry 4 }

gnPdhMonDayUAS OBJECT-TYPE
	SYNTAX  Gauge
	ACCESS  read-only
	STATUS mandatory
	DESCRIPTION
	" The number of Unavailable Seconds
	 per interval of 24 hours."
	::= { gnPdhMonDayEntry 5 }

gnPdhMonDayCV OBJECT-TYPE
	SYNTAX  Gauge
	ACCESS  read-only
	STATUS mandatory
	DESCRIPTION
	" The number of Code Violation Seconds
	 per interval of 24 hours."
	::= { gnPdhMonDayEntry 6}


----

-- ADI: FE Statistics

gnFastEthernetMon OBJECT IDENTIFIER ::= { gnAccess 6 }

gnFastEthernetMonPrivateTable OBJECT-TYPE
	SYNTAX  SEQUENCE OF GnFastEthernetMonPrivateEntry
	ACCESS  not-accessible
	STATUS mandatory
	DESCRIPTION
	"The Fast Ethernet Private Statistics Table."
	::= { gnFastEthernetMon 1 }

gnFastEthernetMonPrivateEntry OBJECT-TYPE
	SYNTAX GnFastEthernetMonPrivateEntry
	ACCESS  not-accessible
	STATUS mandatory
	DESCRIPTION
	"This is an entry in the Fast Ethernet private statistics table."
	INDEX {  ifIndex }
	::= { gnFastEthernetMonPrivateTable 1 }

GnFastEthernetMonPrivateEntry ::=
	    SEQUENCE {
    gnFastEthernetMonPrivateAlignmentErrors
        Counter,
    gnFastEthernetMonPrivateFcsErrors
        Counter,
    gnFastEthernetMonPrivateFrameTooLongs
        Counter
}

gnFastEthernetMonPrivateAlignmentErrors OBJECT-TYPE
              SYNTAX  Counter
              ACCESS  read-only
              STATUS  mandatory
              DESCRIPTION
                      " The number of received packets with an alignment 
					    error (Received frame length is not a multiple 
						of 8 bits, and an FCS error had occurred). "
	::= { gnFastEthernetMonPrivateEntry 1 }

gnFastEthernetMonPrivateFcsErrors OBJECT-TYPE
              SYNTAX  Counter
              ACCESS  read-only
              STATUS  mandatory
              DESCRIPTION
                      " Total number of received packets with a frame check
					    sequence (FCS) or Cycle Redundancy Check (CRC) error. "
	::= { gnFastEthernetMonPrivateEntry 2 }

gnFastEthernetMonPrivateFrameTooLongs OBJECT-TYPE
              SYNTAX  Counter
              ACCESS  read-only
              STATUS  mandatory
              DESCRIPTION
                      " Total number of received frames with an illegal 
					    packet length (>1518 bytes). "
	::= { gnFastEthernetMonPrivateEntry 3 }

---------------

gnFastEthernetMonStdHiTable OBJECT-TYPE
	SYNTAX  SEQUENCE OF GnFastEthernetMonStdHiEntry
	ACCESS  not-accessible
	STATUS mandatory
	DESCRIPTION
	"This table contains the 32 high bits (MSB) of RFC1213 statistics 
	 for Fast Ethernet."
	::= { gnFastEthernetMon 2 }

gnFastEthernetMonStdHiEntry OBJECT-TYPE
	SYNTAX GnFastEthernetMonStdHiEntry
	ACCESS  not-accessible
	STATUS mandatory
	DESCRIPTION
	"This is an entry in the Fast Ethernet 
	 Standard Statistics Table."
	INDEX {  ifIndex }
	::= { gnFastEthernetMonStdHiTable 1 }

GnFastEthernetMonStdHiEntry ::=
	    SEQUENCE {
    gnFastEthernetMonStdHiInOctetsHC
		Counter,
	gnFastEthernetMonStdHiInUcastPktsHC
        Counter,
    gnFastEthernetMonStdHiInNUcastPktsHC
        Counter,
    gnFastEthernetMonStdHiOutOctetsHC
        Counter,
    gnFastEthernetMonStdHiOutUcastPktsHC
        Counter,
    gnFastEthernetMonStdHiOutNUcastPktsHC
        Counter
}

gnFastEthernetMonStdHiInOctetsHC OBJECT-TYPE
              SYNTAX  Counter
              ACCESS  read-only
              STATUS  mandatory
              DESCRIPTION
                      "The 32 MSB of The total number of octets received 
					   on the interface, including framing characters."
	::= { gnFastEthernetMonStdHiEntry 1 }

gnFastEthernetMonStdHiInUcastPktsHC OBJECT-TYPE
              SYNTAX  Counter
              ACCESS  read-only
              STATUS  mandatory
              DESCRIPTION
                      "The 32 MSB of The number of subnetwork-unicast 
					   packets delivered to a higher-layer protocol."
	::= { gnFastEthernetMonStdHiEntry 2 }

gnFastEthernetMonStdHiInNUcastPktsHC OBJECT-TYPE
              SYNTAX  Counter
              ACCESS  read-only
              STATUS  mandatory
              DESCRIPTION
                      "The 32 MSB of The number of non-unicast 
					   (i.e., subnetwork- broadcast or subnetwork-multicast) 
					   packets delivered to a higher-layer protocol."
	::= { gnFastEthernetMonStdHiEntry 3 }

gnFastEthernetMonStdHiOutOctetsHC OBJECT-TYPE
              SYNTAX  Counter
              ACCESS  read-only
              STATUS  mandatory
              DESCRIPTION
                      "The 32 MSB of The total number of octets transmitted 
					   out of the interface, including framing characters."
	::= { gnFastEthernetMonStdHiEntry 4 }

gnFastEthernetMonStdHiOutUcastPktsHC OBJECT-TYPE
              SYNTAX  Counter
              ACCESS  read-only
              STATUS  mandatory
              DESCRIPTION
                      "The 32 MSB of The total number of packets that 
					   higher-level protocols requested be transmitted 
					   to a subnetwork-unicast address, including those 
					   that were discarded or not sent."
	::= { gnFastEthernetMonStdHiEntry 5 }

gnFastEthernetMonStdHiOutNUcastPktsHC OBJECT-TYPE
              SYNTAX  Counter
              ACCESS  read-only
              STATUS  mandatory
              DESCRIPTION
                      "The 32 MSB of The total number of packets that 
					   higher-level protocols requested be transmitted 
					   to a non- unicast (i.e., a subnetwork-broadcast 
					   or subnetwork-multicast) address, including those
                       that were discarded or not sent."
	::= { gnFastEthernetMonStdHiEntry 6 }

gnTrailCfg OBJECT IDENTIFIER ::= { gnAccess 7 }
gnTrailCfgTable OBJECT-TYPE
	SYNTAX  SEQUENCE OF GnTrailCfgEntry
	ACCESS  not-accessible
	STATUS mandatory
	DESCRIPTION
	"This table defines the configuration of the trail ports."
	::= { gnTrailCfg 1 }

gnTrailCfgEntry OBJECT-TYPE
	SYNTAX GnTrailCfgEntry
	ACCESS  not-accessible
	STATUS mandatory
	INDEX { ifIndex }
	::= { gnTrailCfgTable 1 }

GnTrailCfgEntry ::=
	    SEQUENCE {
	gnTrailCfgTrailName
		DisplayString,
	gnTrailCfgProtection
		INTEGER,
	gnTrailCfgLowPathIndex
		INTEGER,
	gnTrailCfgLowPathSide
		INTEGER,
	gnTrailCfgProtectionOptions
		INTEGER,
	gnTrailCfgMismatchJ2	
	    INTEGER,
	gnTrailCfgTransmittedJ2	
	    DisplayString,
	gnTrailCfgExpectedJ2	
	    DisplayString,
	gnTrailCfgReversionMode
		INTEGER,
	gnTrailCfgProtectionUserCommand
		INTEGER,
	gnTrailCfgHoldOffTime
		INTEGER,
	gnTrailCfgOscillationGuardTime
		INTEGER,
	gnTrailCfgWaitToRestoreTime
		INTEGER,
	gnTrailCfgSignalLabelMismatch
		INTEGER,
	gnTrailCfgBERConsAction
		INTEGER
}

gnTrailCfgTrailName OBJECT-TYPE
	SYNTAX  DisplayString(SIZE(0..40))
	ACCESS  read-write
	STATUS mandatory
	DESCRIPTION
	""
	::= { gnTrailCfgEntry 1 }

gnTrailCfgProtection OBJECT-TYPE
	SYNTAX  INTEGER {
		protected(2),
		unprotected(3)
	}
	ACCESS  read-write
	STATUS mandatory
	DESCRIPTION
	""
	DEFVAL { protected}
	::= { gnTrailCfgEntry 2 }

gnTrailCfgLowPathIndex OBJECT-TYPE
	SYNTAX  INTEGER
	ACCESS  read-write
	STATUS mandatory
	DESCRIPTION
	"This parameter indicates the K.L.M index.
	It includes 3 digits:
	K - most significant digit, L - next digit, 
	M - last significant digit. 
	For E1 ports (SDH):   K=1..3 ; L=1..7 ; M=1..3.
	For T1 ports (Sonet): K=1..3 ; L=1..7 ; M=1..4.
	For DS3/E3: 		  K=1..3 ; L=M=0.
	If there is no K.L.M index: K=L=M=0.
	Example: for mapping an E1 port to K.L.M = 2.5.3, write 253."
	::= { gnTrailCfgEntry 3 }

gnTrailCfgLowPathSide OBJECT-TYPE
	SYNTAX  INTEGER {
				east(2),
             	west(3)
		}
        ACCESS  read-write
        STATUS mandatory
	    DEFVAL	{east}
        ::= { gnTrailCfgEntry 4 }

gnTrailCfgProtectionOptions OBJECT-TYPE
	SYNTAX  INTEGER {
				inhibit(2),
             	auto(3)
		}
        ACCESS  read-write
        STATUS mandatory
	    DEFVAL	{auto}
        ::= { gnTrailCfgEntry 5 }

gnTrailCfgMismatchJ2 OBJECT-TYPE
	SYNTAX  INTEGER{
		sendAlarm(2),
		sendAIS(3),
		ignoreAlarm(4)
	}
	ACCESS  read-write
	STATUS mandatory
	DESCRIPTION
	"In case of  J2 mismatch  error, send alarm or send AIS."
	DEFVAL { sendAlarm }
	::= { gnTrailCfgEntry 6 }

gnTrailCfgTransmittedJ2 OBJECT-TYPE
	SYNTAX  DisplayString(SIZE(0..15))
	ACCESS  read-write
	STATUS mandatory
	DESCRIPTION
	"This is the J2 string that would be sent."
	DEFVAL { "J2 J2 J2 J2 J2 " }
	::= { gnTrailCfgEntry 7 }

gnTrailCfgExpectedJ2 OBJECT-TYPE
		SYNTAX  DisplayString(SIZE(0..15))
		ACCESS  read-write
		STATUS mandatory
		DESCRIPTION
	  	"This is the J2 string that is expected to be received."
		DEFVAL { "J2 J2 J2 J2 J2 " }
		::= { gnTrailCfgEntry 8 }

gnTrailCfgReversionMode OBJECT-TYPE
	SYNTAX  INTEGER {
				revertive(2),
             	nonRevertive(3)
		}
        ACCESS  read-write
        STATUS mandatory
	    DEFVAL	{nonRevertive}
        ::= { gnTrailCfgEntry 9 }

	
gnTrailCfgProtectionUserCommand OBJECT-TYPE
	SYNTAX  INTEGER {
				noAction(2),
             	switchToProtection(3),
				switchToWorking(4)
		}
        ACCESS  read-write
        STATUS mandatory
	    DEFVAL	{noAction}
        ::= { gnTrailCfgEntry 10 }

gnTrailCfgHoldOffTime OBJECT-TYPE
	SYNTAX  INTEGER (0..20000)
        ACCESS  read-write
        STATUS mandatory
		DESCRIPTION
	  	"This is the hold-off time in milliseconds.
		 Possible values: 0..20000, 100 mSec steps. "
	    DEFVAL	{0}
        ::= { gnTrailCfgEntry 11 }

	
gnTrailCfgOscillationGuardTime OBJECT-TYPE
	SYNTAX  INTEGER (0..60)
        ACCESS  read-write
        STATUS mandatory
		DESCRIPTION
	  	"This is the oscillation guard time in seconds.
		 Possible values: 0..60. "
	    DEFVAL	{0}
        ::= { gnTrailCfgEntry 12 }

	
gnTrailCfgWaitToRestoreTime OBJECT-TYPE
	SYNTAX  INTEGER (5..12)
        ACCESS  read-write
        STATUS mandatory
		DESCRIPTION
	  	"This is the wait-to-restore time in minutes.
		 Possible values: 5..12. "
	    DEFVAL	{5}
        ::= { gnTrailCfgEntry 13 }

gnTrailCfgSignalLabelMismatch OBJECT-TYPE
	SYNTAX  INTEGER{
		sendAlarm(2),
		sendAIS(3)
	}
        ACCESS  read-write
        STATUS mandatory
		DESCRIPTION
  		" In case of a V5 mismatch error, send or don't send AIS."
	    DEFVAL	{ sendAlarm }
        ::= { gnTrailCfgEntry 14 }

gnTrailCfgBERConsAction OBJECT-TYPE
	SYNTAX  INTEGER{
		sendAlarm(2),
		sendAISDoPathProtection(3),
		doPathProtection(4)
	}
        ACCESS  read-write
        STATUS mandatory
		DESCRIPTION
  		"  "
	    DEFVAL	{ doPathProtection }
        ::= { gnTrailCfgEntry 15 }
--------------

gnTribCfg OBJECT IDENTIFIER ::= { gnAccess 8 }
gnTribCfgTable OBJECT-TYPE
	SYNTAX  SEQUENCE OF GnTribCfgEntry
	ACCESS  not-accessible
	STATUS mandatory
	DESCRIPTION
	"This table defines the configuration of the virtual trails in the Trib STM-1."
	::= { gnTribCfg 1 }

gnTribCfgEntry OBJECT-TYPE
	SYNTAX GnTribCfgEntry
	ACCESS  not-accessible
	STATUS mandatory
	INDEX { ifIndex }
	::= { gnTribCfgTable 1 }

GnTribCfgEntry ::=
	    SEQUENCE {
	gnTribCfgLowPathIndex
		INTEGER,
	gnTribCfgLowPathSide
		INTEGER,
	gnTribCfgProtection
		INTEGER,
	gnTribCfgProtectionOptions
		INTEGER,
	gnTribCfgReversionMode
		INTEGER,
	gnTribCfgProtectionUserCommand
		INTEGER,
	gnTribCfgHoldOffTime
		INTEGER,
	gnTribCfgOscillationGuardTime
		INTEGER,
	gnTribCfgWaitToRestoreTime
		INTEGER,
	gnTribCfgKLM
		INTEGER
--	gnTribCfgBERConsAction			ask Shuki if we need this
--		INTEGER
}

gnTribCfgLowPathIndex OBJECT-TYPE
	SYNTAX  INTEGER
	ACCESS  read-write
	STATUS mandatory
	DESCRIPTION
	"This parameter indicates the K.L.M index.
	It includes 3 digits:
	K - most significant digit, L - next digit, 
	M - last significant digit. 
	For E1 ports (SDH):   K=1..3 ; L=1..7 ; M=1..3.
	For T1 ports (Sonet): K=1..3 ; L=1..7 ; M=1..4.
	For DS3/E3: 		  K=1..3 ; L=M=0.
	If there is no K.L.M index: K=L=M=0.
	Example: for mapping an E1 port to K.L.M = 2.5.3, write 253."
	::= { gnTribCfgEntry 1 }

gnTribCfgLowPathSide OBJECT-TYPE
	SYNTAX  INTEGER {
				east(2),
             	west(3)
		}
        ACCESS  read-write
        STATUS mandatory
	    DEFVAL	{east}
        ::= { gnTribCfgEntry 2 }


gnTribCfgProtection OBJECT-TYPE
	SYNTAX  INTEGER {
		protected(2),
		unprotected(3)
	}
	ACCESS  read-write
	STATUS mandatory
	DESCRIPTION
	""
	DEFVAL { protected}
	::= { gnTribCfgEntry 3 }

gnTribCfgProtectionOptions OBJECT-TYPE
	SYNTAX  INTEGER {
				inhibit(2),
             	auto(3)
		}
        ACCESS  read-write
        STATUS mandatory
	    DEFVAL	{auto}
        ::= { gnTribCfgEntry 4 }

gnTribCfgReversionMode OBJECT-TYPE
	SYNTAX  INTEGER {
				revertive(2),
             	nonRevertive(3)
		}
        ACCESS  read-write
        STATUS mandatory
	    DEFVAL	{nonRevertive}
        ::= { gnTribCfgEntry 5 }

	
gnTribCfgProtectionUserCommand OBJECT-TYPE
	SYNTAX  INTEGER {
				noAction(2),
             	switchToProtection(3),
				switchToWorking(4)
		}
        ACCESS  read-write
        STATUS mandatory
	    DEFVAL	{noAction}
        ::= { gnTribCfgEntry 6 }

gnTribCfgHoldOffTime OBJECT-TYPE
	SYNTAX  INTEGER (0..20000)
        ACCESS  read-write
        STATUS mandatory
		DESCRIPTION
	  	"This is the hold-off time in milliseconds.
		 Possible values: 0..20000, 100 mSec steps. "
	    DEFVAL	{0}
        ::= { gnTribCfgEntry 7 }

	
gnTribCfgOscillationGuardTime OBJECT-TYPE
	SYNTAX  INTEGER (0..60)
        ACCESS  read-write
        STATUS mandatory
		DESCRIPTION
	  	"This is the oscillation guard time in seconds.
		 Possible values: 0..60. "
	    DEFVAL	{0}
        ::= { gnTribCfgEntry 8 }

	
gnTribCfgWaitToRestoreTime OBJECT-TYPE
	SYNTAX  INTEGER (5..12)
        ACCESS  read-write
        STATUS mandatory
		DESCRIPTION
	  	"This is the wait-to-restore time in minutes.
		 Possible values: 5..12. "
	    DEFVAL	{5}
        ::= { gnTribCfgEntry 9 }

gnTribCfgKLM OBJECT-TYPE
		SYNTAX  INTEGER 
        ACCESS  read-write
        STATUS mandatory
		DESCRIPTION
	  	" "
        ::= { gnTribCfgEntry 10 }

-- gnTribCfgBERConsAction OBJECT-TYPE
--	SYNTAX  INTEGER{
--		sendAlarm(2),
--		sendAISDoPathProtection(3),
--		doPathProtection(4)
--	}
--        ACCESS  read-write
--        STATUS mandatory
--		DESCRIPTION
--  		"  "
--	    DEFVAL	{ doPathProtection }
--        ::= { gnTribCfgEntry 15 }
------

-- gnDebug OBJECT IDENTIFIER ::= { ceragon 8 }
--	
--	gnAnalyzer OBJECT IDENTIFIER ::= { gnDebug 1 }
--	
--	gnAnalyzerGeneral OBJECT IDENTIFIER ::= { gnAnalyzer 1 }
--	
-- gnAnalyzerEnable OBJECT-TYPE
-- 	SYNTAX  INTEGER {
--			enable(2),
-- 		disable(3)
--		}
-- 	ACCESS  read-write
-- 	STATUS mandatory
--		DESCRIPTION
--		"."
--		::= { gnAnalyzerGeneral 1 }
--	
--	gnAnalyzerSigType OBJECT-TYPE
-- 	SYNTAX  INTEGER {
-- 		vc12(2),
--			e1t1(3)
-- 	}
--		ACCESS  read-write
-- 	STATUS mandatory
-- 	DESCRIPTION
--		"."
--		::= { gnAnalyzerGeneral 2 }
--	
--	gnAnalyzerSendRsMsHpAlarm OBJECT-TYPE
--		SYNTAX  INTEGER {
-- 		none(0),
-- 		rsLOS(1),
--			rsLOF(2),
-- 		msAIS(4),
--			msRDI(8),
-- 		au1AIS(16),
-- 		au2AIS(32),
--			au3AIS(64),
--			hp1RDI(128),
--			hp2RDI(256),
--			hp3RDI(512),
--			tu1LOM(1024),
-- 		tu2LOM(2048),
-- 		tu3LOM(4096)
--		}
-- 	ACCESS  read-write
--		STATUS mandatory
-- 	DESCRIPTION
-- 	"."
--		::= { gnAnalyzerGeneral 3 }
--	
--	gnAnalyzerSendDefects OBJECT-TYPE
--		SYNTAX  INTEGER {
--			none(0), 
-- 		rsDefects(1),
-- 		msDefects(2),
--			hp1Defects(4),
-- 		hp2Defects(8),
--			hp3Defects(16)
-- 	}
-- 	ACCESS  read-write
--		STATUS mandatory
--		DESCRIPTION
--		"."
--		::= { gnAnalyzerGeneral 4 }
--	
-- gnAnalyzerSendC2 OBJECT-TYPE
-- 	SYNTAX  INTEGER (0..255) 
--		ACCESS  read-write
-- 	STATUS mandatory
--		DESCRIPTION
-- 	"00 - Unequipped.
-- 	 01 - Equipped non specific.
--		 02 - TUG Structure (Default).
--		 03 - Lockked TU.
--		 ...
--		 FF - VC AIS."
--		::= { gnAnalyzerGeneral 5 }
-- 
-- gnAnalyzerReceivedDefects OBJECT-TYPE
--		SYNTAX  INTEGER 
-- 	ACCESS  read-only
--		STATUS mandatory
-- 	DESCRIPTION
-- 	"."
--		::= { gnAnalyzerGeneral 6 }
--	
--	
--	gnAnalyzerPorts OBJECT IDENTIFIER ::=  { gnAnalyzer 2 }
--	
-- gnAnalyzerPortsTable OBJECT-TYPE
-- 	SYNTAX  SEQUENCE OF GnAnalyzerPortsEntry
--		ACCESS  not-accessible
-- 	STATUS mandatory
--		DESCRIPTION
-- 	"."
-- 	::= { gnAnalyzerPorts 1 }
--	
--	gnAnalyzerPortsEntry OBJECT-TYPE
--		SYNTAX GnAnalyzerPortsEntry
--		ACCESS  not-accessible
--		STATUS mandatory
-- 	DESCRIPTION
-- 	"."
--		INDEX { ifIndex }
-- 	::= { gnAnalyzerPortsTable 1 }
--	
-- GnAnalyzerPortsEntry ::=
-- 	    SEQUENCE {
--		gnAnalyzerPortsPrbsEnable
--		     INTEGER,
--		gnAnalyzerPortsSendLpAlarm
--		     INTEGER,
--		gnAnalyzerPortsLockStatus
-- 		INTEGER,
-- 	gnAnalyzerPortsSendDefects
--			INTEGER,
-- 	gnAnalyzerPortsSendV5
--			INTEGER,
-- 	gnAnalyzerPortsReceivedDefects
-- 		INTEGER
--	}
--	
--	
--	gnAnalyzerPortsPrbsEnable OBJECT-TYPE
--		SYNTAX  INTEGER { 
-- 		enable(2), 
-- 		disable(3)
--		}
-- 	ACCESS  read-write
--		STATUS mandatory
-- 	DESCRIPTION
-- 	"."
--		::= { gnAnalyzerPortsEntry 1 }
--	
--	gnAnalyzerPortsSendLpAlarm OBJECT-TYPE
--		SYNTAX  INTEGER { 
--			none(0), 
-- 		lpAis(1),
-- 		lpRdi(2),
--			pdhAis(4)
-- 	}
--		ACCESS  read-write
-- 	STATUS mandatory
-- 	DESCRIPTION
--		"."
--		::= { gnAnalyzerPortsEntry 2 }
--	
--	gnAnalyzerPortsLockStatus OBJECT-TYPE
--		SYNTAX  INTEGER { 
-- 		unlocked(2), 
-- 		locked(3)
--		}
-- 	ACCESS  read-only
--		STATUS mandatory
-- 	DESCRIPTION
-- 	"."
--		::= { gnAnalyzerPortsEntry 3 }
--	
--	gnAnalyzerPortsSendDefects OBJECT-TYPE
--		SYNTAX  INTEGER { 
--			none(2), 
-- 		all(3)
-- 	}
--		ACCESS  read-write
-- 	STATUS mandatory
--		DESCRIPTION
-- 	"."
-- 	::= { gnAnalyzerPortsEntry 4 }
--	
--	gnAnalyzerPortsSendV5 OBJECT-TYPE
--		SYNTAX  INTEGER (0..7) 
--		ACCESS  read-write
--		STATUS mandatory
-- 	DESCRIPTION
-- 	"0 - Unequipped.
--		 1 - Equipped non specific.
-- 	 2 - Asynchronous (Default).
--		 3 - Bit Synchronous.
-- 	 4 - Byte Synchronous.
-- 	 5 - Reserved for future use.
--		 6 - 0.181 test signal (TSS4).
--		 7 - VC AIS."
--		::= { gnAnalyzerPortsEntry 5 }
--	
--	gnAnalyzerPortsReceivedDefects OBJECT-TYPE
-- 	SYNTAX  INTEGER  
-- 	ACCESS  read-only
--		STATUS mandatory
-- 	DESCRIPTION
--		"."
-- 	::= { gnAnalyzerPortsEntry 6 }



gnLastDummy OBJECT IDENTIFIER ::= { ceragon 9 }

gnLastDummyParam OBJECT-TYPE
	SYNTAX  INTEGER
	ACCESS  read-only
	STATUS mandatory
	DESCRIPTION
	" This parameter specifies the end of CERAGON's MIB."
	::= { gnLastDummy 1 }






-- Traps
gnODUTrap TRAP-TYPE
      ENTERPRISE  ceragon
      VARIABLES  {gnGenCfgTrapSeverity , gnGenCfgAlarmText , 
gnGenStatDeviceODUStatus,gnGenCfgIDUSerialNumber }
      DESCRIPTION
	  "The trap is sent every time an alarm occurs in the ODU."
      ::= 1


gnIDUTrap TRAP-TYPE
      ENTERPRISE  ceragon
      VARIABLES  {gnGenCfgTrapSeverity , gnGenCfgAlarmText , 
gnGenStatDeviceIDUStatus,gnGenCfgIDUSerialNumber}
      DESCRIPTION
	  "The trap is sent every time an alarm occurs in the IDU."
      ::= 2

gnSDHTrap TRAP-TYPE
      ENTERPRISE  ceragon
      VARIABLES  {gnGenCfgTrapSeverity , gnGenCfgAlarmText , 
gnGenStatDeviceRSTStatus,gnGenCfgIDUSerialNumber}
      DESCRIPTION
	  "The trap is sent every time an alarm occurs in the Regenerator section 
in
           the SONET/SDH."
      ::= 3

gnACCESSTrap TRAP-TYPE
      ENTERPRISE  ceragon
      VARIABLES  {gnGenCfgTrapSeverity , gnGenCfgAlarmText , 
gnGenCfgIDUSerialNumber}
      DESCRIPTION
	  "The trap is sent every time an alarm occurs in an Access line."
      ::= 4

gnODUTrapCleared TRAP-TYPE
      ENTERPRISE  ceragon
      VARIABLES  {gnGenCfgTrapSeverity , gnGenCfgAlarmText , gnGenStatDeviceODUStatus,gnGenCfgIDUSerialNumber }
      DESCRIPTION
	  "The trap is sent every time an alarm occurs in the ODU."
      ::= 5

gnIDUTrapCleared TRAP-TYPE
      ENTERPRISE  ceragon
      VARIABLES  {gnGenCfgTrapSeverity , gnGenCfgAlarmText , gnGenStatDeviceIDUStatus,gnGenCfgIDUSerialNumber}
      DESCRIPTION
	  "The trap is sent every time an alarm occurs in the IDU."
      ::= 6

gnSDHTrapCleared TRAP-TYPE
      ENTERPRISE  ceragon
      VARIABLES  {gnGenCfgTrapSeverity , gnGenCfgAlarmText , gnGenStatDeviceRSTStatus,gnGenCfgIDUSerialNumber}
      DESCRIPTION
	  "The trap is sent every time an alarm occurs in the Regenerator section in
           the SONET/SDH."
      ::= 7

gnAccessTrapCleared TRAP-TYPE
      ENTERPRISE  ceragon
      VARIABLES  {gnGenCfgTrapSeverity , gnGenCfgAlarmText , gnGenCfgIDUSerialNumber}
      DESCRIPTION
	  "The trap is sent every time an alarm occurs in an Access line."
      ::= 8

-- Traps 9 & 109 are for external use


-- Event Traps

gnLODUPowerFailTrap TRAP-TYPE
      ENTERPRISE  ceragon
      VARIABLES  {gnGenCfgTrapSeverity , gnGenCfgAlarmText , gnOduStatusPowerSupply,gnGenCfgCLLI}
      DESCRIPTION
          "This Trap is sent every time a Local ODU Power fault occurs. "
      ::= 10

gnLODUSynthUnLockTrap TRAP-TYPE
      ENTERPRISE  ceragon
      VARIABLES  {gnGenCfgTrapSeverity , gnGenCfgAlarmText , gnOduStatusSynthesizerVCOLock,gnGenCfgCLLI}
      DESCRIPTION
          "This Trap is sent every time a Local ODU Hardware fault occurs ."
      ::= 11
gnLODUTxLevelOutOfRangeTrap TRAP-TYPE
      ENTERPRISE  ceragon
      VARIABLES  {gnGenCfgTrapSeverity , gnGenCfgAlarmText , gnOduStatusTransmitLevel,gnGenCfgCLLI}
      DESCRIPTION
          "This Trap is sent every time a Local ODU TX signal is out of range. "
      ::= 12

gnLODURxLevelOutOfRangeTrap TRAP-TYPE
      ENTERPRISE  ceragon
      VARIABLES  {gnGenCfgTrapSeverity , gnGenCfgAlarmText , gnOduStatusReceiveLevel,gnGenCfgCLLI}
      DESCRIPTION
          "This Trap is sent every time a Local ODU RX signal is out of range. "
      ::= 13

gnLODUExtremeTempTrap TRAP-TYPE
      ENTERPRISE  ceragon
      VARIABLES  {gnGenCfgTrapSeverity , gnGenCfgAlarmText , gnOduStatusFahrenheitTemp,gnGenCfgCLLI}
      DESCRIPTION
          "This Trap is sent every time a Local ODU extreme temperature event occurs. "
      ::= 14

gnLIDUPowerFailTrap TRAP-TYPE
      ENTERPRISE  ceragon
      VARIABLES  {gnGenCfgTrapSeverity , gnGenCfgAlarmText , gnGenStatDevicePowerSupply,gnGenCfgCLLI}
      DESCRIPTION
          "This Trap is sent every time a Local IDU Power fault occurs. "
      ::= 15

gnLCableFaultTrap TRAP-TYPE
      ENTERPRISE  ceragon
      VARIABLES  {gnGenCfgTrapSeverity , gnGenCfgAlarmText , gnGenStatDeviceCable,gnGenCfgCLLI}
      DESCRIPTION
          "This Trap is sent every time a Local IDU-ODU cable fault occurs."
      ::= 16

gnLModemFailTrap TRAP-TYPE
      ENTERPRISE  ceragon
      VARIABLES  {gnGenCfgTrapSeverity , gnGenCfgAlarmText , gnGenCfgCLLI}
      DESCRIPTION
          "This Trap is sent every time a Local Modem faults occurs."
      ::= 17

gnLIDUExtremeTempTrap TRAP-TYPE
      ENTERPRISE  ceragon
      VARIABLES  {gnGenCfgTrapSeverity , gnGenCfgAlarmText , gnGenStatDeviceFahrenheitTemp,gnGenCfgCLLI}
      DESCRIPTION
          "This Trap is sent every time a Local IDU extreme temperature event occurs. "
      ::=  18

gnLLoopbackOnTrap TRAP-TYPE
      ENTERPRISE  ceragon
      VARIABLES  {gnGenCfgTrapSeverity , gnGenCfgAlarmText , gnGenCfgCLLI}
      DESCRIPTION
          "This Trap is sent every time a Local Loopback is activated."
      ::=  19

gnLRemoteCommFaultTrap TRAP-TYPE
      ENTERPRISE  ceragon
      VARIABLES  {gnGenCfgTrapSeverity , gnGenCfgAlarmText , gnGenCfgCLLI}
      DESCRIPTION
          "This Trap is sent every time the remote communication is disconnected. "
      ::=  20

gnLTestRunningTrap TRAP-TYPE
      ENTERPRISE  ceragon
      VARIABLES  {gnGenCfgTrapSeverity , gnGenCfgAlarmText , gnRstCfgTestActivate,gnGenCfgCLLI}
      DESCRIPTION
          "This Trap is sent every time a Local SDH/SONET test is activated. "
      ::=  21

gnLLOFTrap TRAP-TYPE
      ENTERPRISE  ceragon
      VARIABLES  {ifIndex, gnGenCfgTrapSeverity , gnGenCfgAlarmText , gnGenCfgCLLI}
      DESCRIPTION
          "This Trap is sent every time a Local Loss of Frame alarm occurs."
      ::=  22

gnLLOSTrap TRAP-TYPE
      ENTERPRISE  ceragon
      VARIABLES  {ifIndex, gnGenCfgTrapSeverity , gnGenCfgAlarmText , gnGenCfgCLLI}
      DESCRIPTION
          "This Trap is sent every time a Local Loss of signal alarm occurs."
      ::=  23

gnLTIMTrap TRAP-TYPE
      ENTERPRISE  ceragon
      VARIABLES  {ifIndex, gnGenCfgTrapSeverity , gnGenCfgAlarmText , gnGenCfgCLLI}
      DESCRIPTION
          "This Trap is sent every time a Local Trace Identifier Mismatch alarm occurs."
      ::=  24

gnLEXCTrap TRAP-TYPE
      ENTERPRISE  ceragon
      VARIABLES  {ifIndex, gnGenCfgTrapSeverity , gnGenCfgAlarmText , gnRstStatBERCur ,gnGenCfgCLLI}
      DESCRIPTION
          "This Trap is sent every time a Local Excessive BER alarm is raised. "
      ::= 25

gnLSDTrap TRAP-TYPE
      ENTERPRISE  ceragon
      VARIABLES  {ifIndex, gnGenCfgTrapSeverity , gnGenCfgAlarmText , gnRstStatBERCur,gnGenCfgCLLI}
      DESCRIPTION							  
          "This Trap is sent every time a Local Signal Degrade alarm is raised."
      ::= 26

gnLRcvAisTrap TRAP-TYPE
      ENTERPRISE  ceragon
      VARIABLES  {ifIndex, gnGenCfgTrapSeverity , gnGenCfgAlarmText , gnGenCfgCLLI}
      DESCRIPTION
          "This Trap is sent every time the local terminal receives an Alarm Indication Signal (AIS)."
      ::= 27

gnLUnExpTrap TRAP-TYPE
      ENTERPRISE  ceragon
      VARIABLES  {ifIndex, gnGenCfgTrapSeverity , gnGenCfgAlarmText , gnGenCfgCLLI}
      DESCRIPTION
          "This Trap is sent every time a Local terminal receives an unexpected signal."
      ::= 28

gnLLocTrap TRAP-TYPE
      ENTERPRISE  ceragon
      VARIABLES  {ifIndex, gnGenCfgTrapSeverity , gnGenCfgAlarmText , gnGenCfgCLLI}
      DESCRIPTION
          "This Trap is sent every time a Local Loss of Clock alarm occurs."
      ::= 29

---
gnLLopTrap TRAP-TYPE
      ENTERPRISE  ceragon
      VARIABLES  {ifIndex, gnGenCfgTrapSeverity , gnGenCfgAlarmText , gnGenCfgCLLI}
      DESCRIPTION
          "This Trap is sent every time a Local Loss of pointer alarm occurs."
      ::= 30

gnLRdiTrap TRAP-TYPE
      ENTERPRISE  ceragon
      VARIABLES  {ifIndex, gnGenCfgTrapSeverity , gnGenCfgAlarmText , gnGenCfgCLLI}
      DESCRIPTION
          "This Trap is sent every time the local terminal receives a Remote Defect Identifier signal (RDI). "
      ::= 31

gnLSlmTrap TRAP-TYPE
      ENTERPRISE  ceragon
      VARIABLES  {ifIndex, gnGenCfgTrapSeverity , gnGenCfgAlarmText , gnGenCfgCLLI}
      DESCRIPTION
          "This Trap is sent every time a Local Signal (Payload) Label Mismatch alarm occurs."
      ::= 32

gnLUnqTrap TRAP-TYPE
      ENTERPRISE  ceragon
      VARIABLES  {ifIndex, gnGenCfgTrapSeverity , gnGenCfgAlarmText , gnGenCfgCLLI}
      DESCRIPTION
          "This Trap is sent every time a Local unequipped signal is received. "
      ::= 33

---
gnLExternalAlarm1OnTrap TRAP-TYPE
      ENTERPRISE  ceragon
      VARIABLES  {gnGenCfgTrapSeverity , gnGenCfgAlarmText , gnGenStatDeviceDryContact,gnGenCfgCLLI}
      DESCRIPTION
          "This Trap is sent every time a Local External alarm 1 is raised. "
      ::= 34

gnLExternalAlarm2OnTrap TRAP-TYPE
      ENTERPRISE  ceragon
      VARIABLES  {gnGenCfgTrapSeverity , gnGenCfgAlarmText , gnGenStatDeviceDryContact,gnGenCfgCLLI}
      DESCRIPTION
          "This Trap is sent every time a Local External alarm 2 is raised. "
      ::= 35

gnLExternalAlarm3OnTrap TRAP-TYPE
      ENTERPRISE  ceragon
      VARIABLES  {gnGenCfgTrapSeverity , gnGenCfgAlarmText , gnGenStatDeviceDryContact,gnGenCfgCLLI}
      DESCRIPTION
          "This Trap is sent every time a Local External alarm 3 is raised. "
      ::= 36

gnLExternalAlarm4OnTrap TRAP-TYPE
      ENTERPRISE  ceragon
      VARIABLES  {gnGenCfgTrapSeverity , gnGenCfgAlarmText , gnGenStatDeviceDryContact,gnGenCfgCLLI}
      DESCRIPTION
          "This Trap is sent every time a Local External alarm 4 is raised. "
      ::= 37

gnLExternalAlarm5OnTrap TRAP-TYPE
      ENTERPRISE  ceragon
      VARIABLES  {gnGenCfgTrapSeverity , gnGenCfgAlarmText , gnGenStatDeviceDryContact,gnGenCfgCLLI}
      DESCRIPTION
          "This Trap is sent every time a Local External alarm 5 is raised. "
      ::= 38

gnLExternalAlarm6OnTrap TRAP-TYPE
      ENTERPRISE  ceragon
      VARIABLES  {gnGenCfgTrapSeverity , gnGenCfgAlarmText , gnGenStatDeviceDryContact,gnGenCfgCLLI}
      DESCRIPTION
          "This Trap is sent every time a Local External alarm 6 is raised. "
      ::= 39

gnLExternalAlarm7OnTrap TRAP-TYPE
      ENTERPRISE  ceragon
      VARIABLES  {gnGenCfgTrapSeverity , gnGenCfgAlarmText , gnGenStatDeviceDryContact,gnGenCfgCLLI}
      DESCRIPTION
          "This Trap is sent every time a Local External alarm 7 is raised. "
      ::= 40

gnLExternalAlarm8OnTrap TRAP-TYPE
      ENTERPRISE  ceragon
      VARIABLES  {gnGenCfgTrapSeverity , gnGenCfgAlarmText , gnGenStatDeviceDryContact,gnGenCfgCLLI}
      DESCRIPTION
          "This Trap is sent every time a Local External alarm 8 is raised. "
      ::= 41


gnLSystemFaultTrap TRAP-TYPE
      ENTERPRISE  ceragon
      VARIABLES  {gnGenCfgTrapSeverity , gnGenCfgAlarmText , gnGenStatInternalCommunication,gnGenCfgCLLI}
      DESCRIPTION
          "This Trap is sent every time a Local System fault occurs."
      ::= 42

gnLTftpFaultTrap TRAP-TYPE
      ENTERPRISE  ceragon
      VARIABLES  {gnGenCfgTrapSeverity , gnGenCfgAlarmText , gnGenCfgCLLI}
      DESCRIPTION
          "This Trap is sent every time a Local TFTP Download fails."
      ::= 43

gnLInternalDownloadFaultTrap TRAP-TYPE
      ENTERPRISE  ceragon
      VARIABLES  {gnGenCfgTrapSeverity , gnGenCfgAlarmText , gnGenCfgCLLI}
      DESCRIPTION
          "This Trap is sent every time a Local internal Download fails."
      ::= 44

gnLIntralinkFaultTrap TRAP-TYPE
      ENTERPRISE  ceragon
      VARIABLES  {gnGenCfgTrapSeverity , gnGenCfgAlarmText , gnGenCfgCLLI}
      DESCRIPTION
          "This Trap is sent every time a Local intra-link download fails."
      ::= 45

gnLConfMismatchTrap TRAP-TYPE
      ENTERPRISE  ceragon
      VARIABLES  {gnGenCfgTrapSeverity , gnGenCfgAlarmText , gnGenCfgCLLI}
      DESCRIPTION
          "This Trap is sent every time a Local configuration mismatch fault occurs."
      ::= 46

gnLProtectSwitchFaultTrap TRAP-TYPE
      ENTERPRISE  ceragon
      VARIABLES  {gnGenCfgTrapSeverity , gnGenCfgAlarmText , gnGenCfgCLLI}
      DESCRIPTION
          "This Trap is sent every time a Local Protection fault is raised."
      ::= 47

gnLProtectCableFaultTrap TRAP-TYPE
      ENTERPRISE  ceragon
      VARIABLES  {gnGenCfgTrapSeverity , gnGenCfgAlarmText , gnGenCfgCLLI}
      DESCRIPTION
          "This Trap is sent every time a Local protection cable fault is raised."
      ::= 48

gnLHeartBeatTrap  TRAP-TYPE
      ENTERPRISE  ceragon
      VARIABLES  {gnGenCfgTrapSeverity , gnGenCfgAlarmText , gnGenCfgCLLI}
      DESCRIPTION
          "This Trap is a periodic heart beat trap."
      ::= 49

gnLLomTrap TRAP-TYPE
      ENTERPRISE  ceragon
      VARIABLES  {ifIndex, gnGenCfgTrapSeverity , gnGenCfgAlarmText , gnGenCfgCLLI}
      DESCRIPTION
          "This Trap is sent every time a Local Loss of Multi-frame alarm occurs."
      ::= 50

--gnLHitlessProblemTrap TRAP-TYPE
--      ENTERPRISE  ceragon
--      VARIABLES  {gnGenCfgTrapSeverity , gnGenCfgAlarmText , gnGenCfgCLLI}
--      DESCRIPTION
--          "This Trap is sent every time a Local Hitless fault occurs."
--      ::= 51

gnLHitlessRadioLofTrap TRAP-TYPE
      ENTERPRISE  ceragon
      VARIABLES  {gnGenCfgTrapSeverity , gnGenCfgAlarmText , gnGenCfgCLLI}
      DESCRIPTION
          "This Trap is sent every time a Local Hitless RadioLOF fault occurs."
      ::= 52

gnLHitlessCableDisconnectTrap TRAP-TYPE
      ENTERPRISE  ceragon
      VARIABLES  {gnGenCfgTrapSeverity , gnGenCfgAlarmText , gnGenCfgCLLI}
      DESCRIPTION
          "This Trap is sent every time a Local Hitless cable fault is raised. "
      ::= 53
		

gnLPamTrap TRAP-TYPE
      ENTERPRISE  ceragon
      VARIABLES  {ifIndex, gnGenCfgTrapSeverity , gnGenCfgAlarmText , gnGenCfgCLLI}
      DESCRIPTION
          "This Trap is sent when system in MSP Protection Architecture Mismatch."
      ::=  54
		
gnLScmTrap TRAP-TYPE
      ENTERPRISE  ceragon
      VARIABLES  {ifIndex, gnGenCfgTrapSeverity , gnGenCfgAlarmText , gnGenCfgCLLI}
      DESCRIPTION
          "This Trap is sent when there is a MSP Selector Channel Mismatch (K1,K2)."
      ::=  55

gnLInvTrap TRAP-TYPE
      ENTERPRISE  ceragon
      VARIABLES  {ifIndex, gnGenCfgTrapSeverity , gnGenCfgAlarmText , gnGenCfgCLLI}
      DESCRIPTION
          "This Trap indicates that the received K1 byte is invalid (MSP)."
      ::=  56

gnLInbandTrap TRAP-TYPE
      ENTERPRISE  ceragon
      VARIABLES  {ifIndex, gnGenCfgTrapSeverity , gnGenCfgAlarmText , gnGenCfgCLLI}
      DESCRIPTION
          "This Trap is sent when the Inband PPP link goes down."
      ::=  57

-- Traps 58-61 and 158-161 are saved for phos.

-- ********************

-- Traps 9 & 109 are for external use

gnLODUPowerOkTrap TRAP-TYPE
      ENTERPRISE  ceragon
      VARIABLES  {gnGenCfgTrapSeverity , gnGenCfgAlarmText , gnOduStatusPowerSupply,gnGenCfgCLLI}
      DESCRIPTION
          "This Trap is sent every time a Local ODU Power fault cleared."
      ::= 110

gnLODUSynthLockTrap TRAP-TYPE
      ENTERPRISE  ceragon
      VARIABLES  {gnGenCfgTrapSeverity , gnGenCfgAlarmText , gnOduStatusSynthesizerVCOLock,gnGenCfgCLLI}
      DESCRIPTION
          "This Trap is sent every time a Local ODU Hardware fault is cleared."
      ::= 111
gnLODUTxLevelInRangeTrap TRAP-TYPE
      ENTERPRISE  ceragon
      VARIABLES  {gnGenCfgTrapSeverity , gnGenCfgAlarmText , gnOduStatusTransmitLevel,gnGenCfgCLLI}
      DESCRIPTION
          "This Trap is sent every time a Local ODU TX signal is in range. "
      ::= 112

gnLODURxLevelInRangeTrap TRAP-TYPE
      ENTERPRISE  ceragon
      VARIABLES  {gnGenCfgTrapSeverity , gnGenCfgAlarmText , gnOduStatusReceiveLevel,gnGenCfgCLLI}
      DESCRIPTION
          "This Trap is sent every time a Local ODU RX signal is in range. "
      ::= 113

gnLODUNormalTempTrap TRAP-TYPE
      ENTERPRISE  ceragon
      VARIABLES  {gnGenCfgTrapSeverity , gnGenCfgAlarmText , gnOduStatusFahrenheitTemp,gnGenCfgCLLI}
      DESCRIPTION
          "This Trap is sent every time a Local ODU returns to normal temperature."
      ::= 114

gnLIDUPowerOkTrap TRAP-TYPE
      ENTERPRISE  ceragon
      VARIABLES  {gnGenCfgTrapSeverity , gnGenCfgAlarmText , gnGenStatDevicePowerSupply,gnGenCfgCLLI}
      DESCRIPTION
          "This Trap is sent every time a Local IDU Power fault is cleared."
      ::= 115


gnLCableOkTrap TRAP-TYPE
      ENTERPRISE  ceragon
      VARIABLES  {gnGenCfgTrapSeverity , gnGenCfgAlarmText , gnGenStatDeviceCable,gnGenCfgCLLI}
      DESCRIPTION
          "This Trap is sent every time a Local IDU-ODU cable fault is cleared."
      ::= 116

gnLModemOkTrap TRAP-TYPE
      ENTERPRISE  ceragon
      VARIABLES  {gnGenCfgTrapSeverity , gnGenCfgAlarmText , gnGenCfgCLLI}
      DESCRIPTION
          "This Trap is sent every time a Local Modem faults is cleared. "
      ::= 117


gnLIDUNormalTempTrap TRAP-TYPE
      ENTERPRISE  ceragon
      VARIABLES  {gnGenCfgTrapSeverity , gnGenCfgAlarmText , gnGenStatDeviceFahrenheitTemp,gnGenCfgCLLI}
      DESCRIPTION
          "This Trap is sent every time a Local IDU returns to normal temperature."
      ::= 118

gnLLoopbackOffTrap TRAP-TYPE
      ENTERPRISE  ceragon
      VARIABLES  {gnGenCfgTrapSeverity , gnGenCfgAlarmText , gnGenCfgCLLI}
      DESCRIPTION
          "This Trap is sent every time a Local Loopback is cleared."
      ::= 119

gnLRemoteCommOkTrap TRAP-TYPE
      ENTERPRISE  ceragon
      VARIABLES  {gnGenCfgTrapSeverity , gnGenCfgAlarmText , gnGenCfgCLLI}
      DESCRIPTION
          "This Trap is sent every time the remote communication is re-connected."
      ::=  120

gnLNoTestRunningTrap TRAP-TYPE
      ENTERPRISE  ceragon
      VARIABLES  {gnGenCfgTrapSeverity , gnGenCfgAlarmText , gnRstCfgTestActivate,gnGenCfgCLLI}
      DESCRIPTION
          "This Trap is sent every time a Local SDH/SONET test is cleared."
      ::= 121

gnLNoLOFTrap TRAP-TYPE
      ENTERPRISE  ceragon
      VARIABLES  {ifIndex, gnGenCfgTrapSeverity , gnGenCfgAlarmText , gnGenCfgCLLI}
      DESCRIPTION
          "This Trap is sent every time a Local Loss of Frame alarm is cleared."
      ::=  122

gnLNoLOSTrap TRAP-TYPE
      ENTERPRISE  ceragon
      VARIABLES  {ifIndex, gnGenCfgTrapSeverity , gnGenCfgAlarmText , gnGenCfgCLLI}
      DESCRIPTION
          "This Trap is sent every time a Local Loss of Signal alarm is cleared."
      ::=  123

gnLNoTIMTrap TRAP-TYPE
      ENTERPRISE  ceragon
      VARIABLES  {ifIndex, gnGenCfgTrapSeverity , gnGenCfgAlarmText , gnGenCfgCLLI}
      DESCRIPTION
          "This Trap is sent every time a Local Trace Identifier Mismatch alarm is cleared."
      ::= 124

gnLNoEXCTrap TRAP-TYPE
      ENTERPRISE  ceragon
      VARIABLES  {ifIndex, gnGenCfgTrapSeverity , gnGenCfgAlarmText , gnRstStatBERCur,gnGenCfgCLLI}
      DESCRIPTION
          "This Trap is sent every time a Local Excessive BER alarm is cleared. "
      ::= 125

gnLNoSDTrap TRAP-TYPE
      ENTERPRISE  ceragon
      VARIABLES  {ifIndex, gnGenCfgTrapSeverity , gnGenCfgAlarmText , gnRstStatBERCur,gnGenCfgCLLI}
      DESCRIPTION
          "This Trap is sent every time a Local Signal Degrade alarm is cleared."
      ::= 126

gnLNoAisTrap TRAP-TYPE
      ENTERPRISE  ceragon
      VARIABLES  {ifIndex, gnGenCfgTrapSeverity , gnGenCfgAlarmText , gnGenCfgCLLI}
      DESCRIPTION
          "This Trap is sent every time the local terminal stops receiving an Alarm Indication Signal (AIS)."
      ::= 127

gnLNoUnExpTrap TRAP-TYPE
      ENTERPRISE  ceragon
      VARIABLES  {ifIndex, gnGenCfgTrapSeverity , gnGenCfgAlarmText , gnGenCfgCLLI}
      DESCRIPTION
          "This Trap is sent every time a Local terminal stops receiving an unexpected signal."
      ::= 128

gnLNoLocTrap TRAP-TYPE
      ENTERPRISE  ceragon
      VARIABLES  {ifIndex, gnGenCfgTrapSeverity , gnGenCfgAlarmText , gnGenCfgCLLI}
      DESCRIPTION
          "This Trap is sent every time a Local Loss of Carrier (On the FE interfaces) alarm is cleared."
      ::= 129

---
gnLNoLopTrap TRAP-TYPE
      ENTERPRISE  ceragon
      VARIABLES  {ifIndex, gnGenCfgTrapSeverity , gnGenCfgAlarmText , gnGenCfgCLLI}
      DESCRIPTION
          "This Trap is sent every time a Local Loss of pointer alarm is cleared."
      ::= 130

gnLNoRdiTrap TRAP-TYPE
      ENTERPRISE  ceragon
      VARIABLES  {ifIndex, gnGenCfgTrapSeverity , gnGenCfgAlarmText , gnGenCfgCLLI}
      DESCRIPTION
          "This Trap is sent every time the local terminal stops receiving a Remote Defect Identifier signal (RDI)."
      ::= 131

gnLNoSlmTrap TRAP-TYPE
      ENTERPRISE  ceragon
      VARIABLES  {ifIndex, gnGenCfgTrapSeverity , gnGenCfgAlarmText , gnGenCfgCLLI}
      DESCRIPTION
          "This Trap is sent every time a Local Signal (Payload) Label Mismatch alarm is cleared. "
      ::= 132

gnLNoUnqTrap TRAP-TYPE
      ENTERPRISE  ceragon
      VARIABLES  {ifIndex, gnGenCfgTrapSeverity , gnGenCfgAlarmText , gnGenCfgCLLI}
      DESCRIPTION
          "This Trap is sent every time a Local terminal start receiving an equipped signal. "
      ::= 133

---

gnLExternalAlarm1OffTrap TRAP-TYPE
      ENTERPRISE  ceragon
      VARIABLES  {gnGenCfgTrapSeverity , gnGenCfgAlarmText , gnGenStatDeviceDryContact,gnGenCfgCLLI}
      DESCRIPTION
          "This Trap is sent every time a Local External alarm 1 is cleared. "
      ::= 134


gnLExternalAlarm2OffTrap TRAP-TYPE
      ENTERPRISE  ceragon
      VARIABLES  {gnGenCfgTrapSeverity , gnGenCfgAlarmText , gnGenStatDeviceDryContact,gnGenCfgCLLI}
      DESCRIPTION
          "This Trap is sent every time a Local External alarm 2 is cleared. "
      ::= 135


gnLExternalAlarm3OffTrap TRAP-TYPE
      ENTERPRISE  ceragon
      VARIABLES  {gnGenCfgTrapSeverity , gnGenCfgAlarmText , gnGenStatDeviceDryContact,gnGenCfgCLLI}
      DESCRIPTION
          "This Trap is sent every time a Local External alarm 3 is cleared. "
      ::= 136


gnLExternalAlarm4OffTrap TRAP-TYPE
      ENTERPRISE  ceragon
      VARIABLES  {gnGenCfgTrapSeverity , gnGenCfgAlarmText , gnGenStatDeviceDryContact,gnGenCfgCLLI}
      DESCRIPTION
          "This Trap is sent every time a Local External alarm 4 is cleared. "
      ::= 137


gnLExternalAlarm5OffTrap TRAP-TYPE
      ENTERPRISE  ceragon
      VARIABLES  {gnGenCfgTrapSeverity , gnGenCfgAlarmText , gnGenStatDeviceDryContact,gnGenCfgCLLI}
      DESCRIPTION
          "This Trap is sent every time a Local External alarm 5 is cleared. "
      ::= 138


gnLExternalAlarm6OffTrap TRAP-TYPE
      ENTERPRISE  ceragon
      VARIABLES  {gnGenCfgTrapSeverity , gnGenCfgAlarmText , gnGenStatDeviceDryContact,gnGenCfgCLLI}
      DESCRIPTION
          "This Trap is sent every time a Local External alarm 6 is cleared. "
      ::= 139


gnLExternalAlarm7OffTrap TRAP-TYPE
      ENTERPRISE  ceragon
      VARIABLES  {gnGenCfgTrapSeverity , gnGenCfgAlarmText , gnGenStatDeviceDryContact,gnGenCfgCLLI}
      DESCRIPTION
          "This Trap is sent every time a Local External alarm 7 is cleared. "
      ::= 140


gnLExternalAlarm8OffTrap TRAP-TYPE
      ENTERPRISE  ceragon
      VARIABLES  {gnGenCfgTrapSeverity , gnGenCfgAlarmText , gnGenStatDeviceDryContact,gnGenCfgCLLI}
      DESCRIPTION
          "This Trap is sent every time a Local External alarm 8 is cleared."
      ::= 141

gnLSystemOkTrap TRAP-TYPE
      ENTERPRISE  ceragon
      VARIABLES  {gnGenCfgTrapSeverity , gnGenCfgAlarmText , gnGenStatInternalCommunication,gnGenCfgCLLI}
      DESCRIPTION
          "This Trap is sent every time a Local System fault is cleared."
      ::= 142

gnLTftpOkTrap TRAP-TYPE
      ENTERPRISE  ceragon
      VARIABLES  {gnGenCfgTrapSeverity , gnGenCfgAlarmText , gnGenCfgCLLI}
      DESCRIPTION
          "This Trap is sent every time a Local TFTP Download succeeded."
      ::= 143

gnLInternalDownloadOkTrap TRAP-TYPE
      ENTERPRISE  ceragon
      VARIABLES  {gnGenCfgTrapSeverity , gnGenCfgAlarmText , gnGenCfgCLLI}
      DESCRIPTION
          "This Trap is sent every time a Local internal Download succeeded."
      ::= 144

gnLIntralinkOkTrap TRAP-TYPE
      ENTERPRISE  ceragon
      VARIABLES  {gnGenCfgTrapSeverity , gnGenCfgAlarmText , gnGenCfgCLLI}
      DESCRIPTION
          "This Trap is sent every time a Local intra-link download succeeded."
      ::= 145

gnLNoConfMismatchTrap TRAP-TYPE
      ENTERPRISE  ceragon
      VARIABLES  {gnGenCfgTrapSeverity , gnGenCfgAlarmText , gnGenCfgCLLI}
      DESCRIPTION
          "This Trap is sent every time a Local configuration mismatch fault is cleared."
      ::= 146

-- "positive" traps are not being send when protection switch occurs.
-- gnLProtectSwitchOkTrap TRAP-TYPE
--     ENTERPRISE  ceragon
--     VARIABLES  {gnGenCfgTrapSeverity , gnGenCfgAlarmText , gnGenCfgCLLI}
--     DESCRIPTION
--         "Never sent. "
--     ::= 147

gnLProtectCableOkTrap TRAP-TYPE
      ENTERPRISE  ceragon
      VARIABLES  {gnGenCfgTrapSeverity , gnGenCfgAlarmText , gnGenCfgCLLI}
      DESCRIPTION
          "This Trap is sent every time a Local protection cable fault is cleared."
      ::= 148

gnLLomOkTrap TRAP-TYPE
      ENTERPRISE  ceragon
      VARIABLES  {ifIndex, gnGenCfgTrapSeverity , gnGenCfgAlarmText , gnGenCfgCLLI}
      DESCRIPTION
          "This Trap is sent every time a Local Loss of Multi-frame alarm is cleared."
      ::= 150

--gnLHitlessProblemOKTrap TRAP-TYPE
--      ENTERPRISE  ceragon
--      VARIABLES  {gnGenCfgTrapSeverity , gnGenCfgAlarmText , gnGenCfgCLLI}
--      DESCRIPTION
--          "This Trap is sent every time a Local Hitless fault is cleared."
--      ::= 151

gnLHitlessRadioLofOKTrap TRAP-TYPE
      ENTERPRISE  ceragon
      VARIABLES  {gnGenCfgTrapSeverity , gnGenCfgAlarmText , gnGenCfgCLLI}
      DESCRIPTION
          "This Trap is sent every time a Local Hitless RadioLOF fault is cleared."
      ::= 152

gnLHitlessCableDisconnectOKTrap TRAP-TYPE
      ENTERPRISE  ceragon
      VARIABLES  {gnGenCfgTrapSeverity , gnGenCfgAlarmText , gnGenCfgCLLI}
      DESCRIPTION
          "This Trap is sent every time a Local Hitless cable fault is cleared."
      ::= 153

gnLPamOkTrap TRAP-TYPE
      ENTERPRISE  ceragon
      VARIABLES  {ifIndex, gnGenCfgTrapSeverity , gnGenCfgAlarmText , gnGenCfgCLLI}
      DESCRIPTION
          "This Trap is sent when system in MSP Protection Architecture Mismatch."
      ::=  154
		
gnLScmOkTrap TRAP-TYPE
      ENTERPRISE  ceragon
      VARIABLES  {ifIndex, gnGenCfgTrapSeverity , gnGenCfgAlarmText , gnGenCfgCLLI}
      DESCRIPTION
          "This Trap is sent when there is a MSP Selector Channel Mismatch (K1,K2)."
      ::=  155

gnLInvOkTrap TRAP-TYPE
      ENTERPRISE  ceragon
      VARIABLES  {ifIndex, gnGenCfgTrapSeverity , gnGenCfgAlarmText , gnGenCfgCLLI}
      DESCRIPTION
          "This Trap indicates that the received K1 byte is invalid (MSP)."
      ::=  156

gnLInbandOkTrap TRAP-TYPE
      ENTERPRISE  ceragon
      VARIABLES  {ifIndex, gnGenCfgTrapSeverity , gnGenCfgAlarmText , gnGenCfgCLLI}
      DESCRIPTION
          "This Trap is sent when the Inband PPP link goes up."
      ::=  157

-- Traps 58-61 and 158-161 are saved for phos.





gnRODUPowerFailTrap TRAP-TYPE
      ENTERPRISE  ceragon
      VARIABLES  {gnGenCfgTrapSeverity , gnGenCfgAlarmText , gnOduStatusPowerSupply,gnGenCfgCLLI}
      DESCRIPTION
          "This Trap is sent every time a Remote ODU Power fault occurs."
      ::= 210

gnRODUSynthUnLockTrap TRAP-TYPE
      ENTERPRISE  ceragon
      VARIABLES  {gnGenCfgTrapSeverity , gnGenCfgAlarmText , gnOduStatusSynthesizerVCOLock,gnGenCfgCLLI}
      DESCRIPTION
          "This Trap is sent every time a Remote ODU Hardware fault occurs ."
      ::= 211

gnRODUTxLevelOutOfRangeTrap TRAP-TYPE
      ENTERPRISE  ceragon
      VARIABLES  {gnGenCfgTrapSeverity , gnGenCfgAlarmText , gnOduStatusTransmitLevel,gnGenCfgCLLI}
      DESCRIPTION
          "This Trap is sent every time a Remote ODU TX signal is out of range."
      ::= 212

gnRODURxLevelOutOfRangeTrap TRAP-TYPE
      ENTERPRISE  ceragon
      VARIABLES  {gnGenCfgTrapSeverity , gnGenCfgAlarmText , gnOduStatusReceiveLevel,gnGenCfgCLLI}
      DESCRIPTION
          "This Trap is sent every time a Remote ODU RX signal is out of range."
      ::= 213

gnRODUExtremeTempTrap TRAP-TYPE
      ENTERPRISE  ceragon
      VARIABLES  {gnGenCfgTrapSeverity , gnGenCfgAlarmText , gnOduStatusFahrenheitTemp,gnGenCfgCLLI}
      DESCRIPTION
          "This Trap is sent every time a Remote ODU extreme temperature event occurs."
      ::= 214

gnRIDUPowerFailTrap TRAP-TYPE
      ENTERPRISE  ceragon
      VARIABLES  {gnGenCfgTrapSeverity , gnGenCfgAlarmText , gnGenStatDevicePowerSupply,gnGenCfgCLLI}
      DESCRIPTION
          "This Trap is sent every time a Remote IDU Power fault occurs."
      ::= 215
		  
gnRCableFaultTrap TRAP-TYPE
      ENTERPRISE  ceragon
      VARIABLES  {gnGenCfgTrapSeverity , gnGenCfgAlarmText , gnGenStatDeviceCable,gnGenCfgCLLI}
      DESCRIPTION
          "This Trap is sent every time a Remote IDU-ODU cable fault occurs."
      ::= 216

gnRModemFailTrap TRAP-TYPE
      ENTERPRISE  ceragon
      VARIABLES  {gnGenCfgTrapSeverity , gnGenCfgAlarmText , gnGenCfgCLLI}
      DESCRIPTION
          "This Trap is sent every time a Remote Modem faults occurs."
      ::= 217


gnRIDUExtremeTempTrap TRAP-TYPE
      ENTERPRISE  ceragon
      VARIABLES  {gnGenCfgTrapSeverity , gnGenCfgAlarmText , gnGenStatDeviceFahrenheitTemp,gnGenCfgCLLI}
      DESCRIPTION
          "This Trap is sent every time a Remote IDU extreme temperature event occurs."
      ::= 218

gnRLoopbackOnTrap TRAP-TYPE
      ENTERPRISE  ceragon
      VARIABLES  {gnGenCfgTrapSeverity , gnGenCfgAlarmText , gnGenCfgCLLI}
      DESCRIPTION
          "This Trap is sent every time a Remote Loopback is activated."
      ::= 219

gnRRemoteCommFaultTrap TRAP-TYPE
      ENTERPRISE  ceragon
      VARIABLES  {gnGenCfgTrapSeverity , gnGenCfgAlarmText , gnGenCfgCLLI}
      DESCRIPTION
          "This Trap is sent every time the remote communication is disconnected."
      ::= 220

gnRTestRunningTrap TRAP-TYPE
      ENTERPRISE  ceragon
      VARIABLES  {gnGenCfgTrapSeverity , gnGenCfgAlarmText , gnRstCfgTestActivate,gnGenCfgCLLI}
      DESCRIPTION
          "This Trap is sent every time a Remote SDH/SONET test is activated."
      ::=  221

gnRLOFTrap TRAP-TYPE
      ENTERPRISE  ceragon
      VARIABLES  {ifIndex, gnGenCfgTrapSeverity , gnGenCfgAlarmText , gnGenCfgCLLI}
      DESCRIPTION
          "This Trap is sent every time a Remote Loss of Frame alarm occurs."
      ::=  222

gnRLOSTrap TRAP-TYPE
      ENTERPRISE  ceragon
      VARIABLES  {ifIndex, gnGenCfgTrapSeverity , gnGenCfgAlarmText , gnGenCfgCLLI}
      DESCRIPTION
          "This Trap is sent every time a Remote Loss of signal alarm occurs."
      ::=  223

gnRTIMTrap TRAP-TYPE
      ENTERPRISE  ceragon
      VARIABLES  {ifIndex, gnGenCfgTrapSeverity , gnGenCfgAlarmText , gnGenCfgCLLI}
      DESCRIPTION
          "This Trap is sent every time a Remote Trace Identifier Mismatch alarm occurs."
      ::=  224

gnREXCTrap TRAP-TYPE
      ENTERPRISE  ceragon
      VARIABLES  {ifIndex, gnGenCfgTrapSeverity , gnGenCfgAlarmText , gnRstStatBERCur,gnGenCfgCLLI}
      DESCRIPTION
          "This Trap is sent every time a Remote Excessive BER alarm is raised."
      ::=  225

gnRSDTrap TRAP-TYPE
      ENTERPRISE  ceragon
      VARIABLES  {ifIndex, gnGenCfgTrapSeverity , gnGenCfgAlarmText , gnRstStatBERCur,gnGenCfgCLLI}
      DESCRIPTION
          "This Trap is sent every time a Remote Signal Degrade alarm is raised."
      ::=  226

gnRAisTrap TRAP-TYPE
      ENTERPRISE  ceragon
      VARIABLES  {ifIndex, gnGenCfgTrapSeverity , gnGenCfgAlarmText , gnGenCfgCLLI}
      DESCRIPTION
          "This Trap is sent every time the Remote terminal receives an Alarm Indication Signal (AIS)."
      ::=  227

gnRUnExpTrap TRAP-TYPE
      ENTERPRISE  ceragon
      VARIABLES  {ifIndex, gnGenCfgTrapSeverity , gnGenCfgAlarmText , gnGenCfgCLLI}
      DESCRIPTION
          "This Trap is sent every time a Remote terminal receives an unexpected signal."
      ::=  228

gnRLocTrap TRAP-TYPE
      ENTERPRISE  ceragon
      VARIABLES  {ifIndex, gnGenCfgTrapSeverity , gnGenCfgAlarmText , gnGenCfgCLLI}
      DESCRIPTION
          "This Trap is sent every time a Remote Loss of Carrier (On the FE interfaces) alarm occurs."
      ::=   229

---
gnRLopTrap TRAP-TYPE
      ENTERPRISE  ceragon
      VARIABLES  {ifIndex, gnGenCfgTrapSeverity , gnGenCfgAlarmText , gnGenCfgCLLI}
      DESCRIPTION
          "This Trap is sent every time a Remote Loss of pointer alarm occurs."
      ::= 	230

gnRRdiTrap TRAP-TYPE
      ENTERPRISE  ceragon
      VARIABLES  {ifIndex, gnGenCfgTrapSeverity , gnGenCfgAlarmText , gnGenCfgCLLI}
      DESCRIPTION
          "This Trap is sent every time the Remote terminal receives a Remote Defect Identifier signal (RDI)."
      ::= 	231

gnRSlmTrap TRAP-TYPE
      ENTERPRISE  ceragon
      VARIABLES  {ifIndex, gnGenCfgTrapSeverity , gnGenCfgAlarmText , gnGenCfgCLLI}
      DESCRIPTION
          "This Trap is sent every time a Remote Signal (Payload) Label Mismatch alarm occurs."
      ::= 	232

gnRUnqTrap TRAP-TYPE
      ENTERPRISE  ceragon
      VARIABLES  {ifIndex, gnGenCfgTrapSeverity , gnGenCfgAlarmText , gnGenCfgCLLI}
      DESCRIPTION
          "This Trap is sent every time a Remote unequipped signal is received."
      ::= 	233

---


gnRExternalAlarm1OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 1 is raised."
      ::=  234

gnRExternalAlarm2OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 2 is raised."
      ::=  235

gnRExternalAlarm3OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 3 is raised."
      ::=  236

gnRExternalAlarm4OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 4 is raised."
      ::=  237

gnRExternalAlarm5OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 5 is raised."
      ::=  238

gnRExternalAlarm6OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 6 is raised."
      ::=  239

gnRExternalAlarm7OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 7 is raised."
      ::=  240

gnRExternalAlarm8OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 8 is raised."
      ::=  241

gnRSystemFaultTrap TRAP-TYPE
      ENTERPRISE  ceragon
      VARIABLES  {gnGenCfgTrapSeverity , gnGenCfgAlarmText , gnGenStatInternalCommunication,gnGenCfgCLLI}
      DESCRIPTION
          "This Trap is sent every time a Remote System fault occurs."
      ::=  242

gnRTftpFaultTrap TRAP-TYPE
      ENTERPRISE  ceragon
      VARIABLES  {gnGenCfgTrapSeverity , gnGenCfgAlarmText , gnGenCfgCLLI}
      DESCRIPTION
          "This Trap is sent every time a Remote TFTP Download fails."
      ::= 243

gnRInternalDownloadFaultTrap TRAP-TYPE
      ENTERPRISE  ceragon
      VARIABLES  {gnGenCfgTrapSeverity , gnGenCfgAlarmText , gnGenCfgCLLI}
      DESCRIPTION
          "This Trap is sent every time a Remote internal Download fails."
      ::= 244

gnRIntralinkFaultTrap TRAP-TYPE
      ENTERPRISE  ceragon
      VARIABLES  {gnGenCfgTrapSeverity , gnGenCfgAlarmText , gnGenCfgCLLI}
      DESCRIPTION
          "This Trap is sent every time a Remote intra-link download fails."
      ::= 245

gnRConfMismatchTrap TRAP-TYPE
      ENTERPRISE  ceragon
      VARIABLES  {gnGenCfgTrapSeverity , gnGenCfgAlarmText , gnGenCfgCLLI}
      DESCRIPTION
          "This Trap is sent every time a Remote configuration mismatch fault occurs."
      ::= 246

gnRProtectSwitchFaultTrap TRAP-TYPE
      ENTERPRISE  ceragon
      VARIABLES  {gnGenCfgTrapSeverity , gnGenCfgAlarmText , gnGenCfgCLLI}
      DESCRIPTION
          "This Trap is sent every time a Remote Protection fault is raised."
      ::= 247

gnRProtectCableFaultTrap TRAP-TYPE
      ENTERPRISE  ceragon
      VARIABLES  {gnGenCfgTrapSeverity , gnGenCfgAlarmText , gnGenCfgCLLI}
      DESCRIPTION
          "This Trap is sent every time a Remote protection cable fault is raised."
      ::= 248

gnRHeartBeatTrap  TRAP-TYPE
      ENTERPRISE  ceragon
      VARIABLES  {gnGenCfgTrapSeverity , gnGenCfgAlarmText , gnGenCfgCLLI}
      DESCRIPTION
          "This Trap is a periodic heart beat trap."
      ::= 249

gnRLomTrap TRAP-TYPE
      ENTERPRISE  ceragon
      VARIABLES  {ifIndex, gnGenCfgTrapSeverity , gnGenCfgAlarmText , gnGenCfgCLLI}
      DESCRIPTION
          "This Trap is sent every time a Remote Loss of Multi-frame alarm occurs."
      ::= 250

--gnRHitlessProblemTrap TRAP-TYPE
--      ENTERPRISE  ceragon
--      VARIABLES  {gnGenCfgTrapSeverity , gnGenCfgAlarmText , gnGenCfgCLLI}
--      DESCRIPTION
--          "This Trap is sent every time a Remote Hitless fault occurs."
--     ::= 251

gnRHitlessRadioLofTrap TRAP-TYPE
      ENTERPRISE  ceragon
      VARIABLES  {gnGenCfgTrapSeverity , gnGenCfgAlarmText , gnGenCfgCLLI}
      DESCRIPTION
          "This Trap is sent every time a Remote Hitless RadioLOF fault occurs."
      ::= 252

gnRHitlessCableDisconnectTrap TRAP-TYPE
      ENTERPRISE  ceragon
      VARIABLES  {gnGenCfgTrapSeverity , gnGenCfgAlarmText , gnGenCfgCLLI}
      DESCRIPTION
          "This Trap is sent every time a Remote Hitless cable fault is raised."
      ::= 253

-- 		skip 254-256 	(MSP PAM, SCM, INV)
-- 		skip 257 		(Inband)




gnRODUPowerOkTrap TRAP-TYPE
      ENTERPRISE  ceragon
      VARIABLES  {gnGenCfgTrapSeverity , gnGenCfgAlarmText , gnOduStatusPowerSupply,gnGenCfgCLLI}
      DESCRIPTION
          "This Trap is sent every time a Remote ODU Power fault cleared."
      ::= 310

gnRODUSynthLockTrap TRAP-TYPE
      ENTERPRISE  ceragon
      VARIABLES  {gnGenCfgTrapSeverity , gnGenCfgAlarmText , gnOduStatusSynthesizerVCOLock,gnGenCfgCLLI}
      DESCRIPTION
          "This Trap is sent every time a Remote ODU Hardware fault is cleared."
      ::= 311

gnRODUTxLevelInRangeTrap TRAP-TYPE
      ENTERPRISE  ceragon
      VARIABLES  {gnGenCfgTrapSeverity , gnGenCfgAlarmText , gnOduStatusTransmitLevel,gnGenCfgCLLI}
      DESCRIPTION
          "This Trap is sent every time a Remote ODU TX signal is in range."
      ::= 312

gnRODURxLevelInRangeTrap TRAP-TYPE
      ENTERPRISE  ceragon
      VARIABLES  {gnGenCfgTrapSeverity , gnGenCfgAlarmText , gnOduStatusReceiveLevel,gnGenCfgCLLI}
      DESCRIPTION
          "This Trap is sent every time a Remote ODU RX signal is in range."
      ::= 313

gnRODUNormalTempTrap TRAP-TYPE
      ENTERPRISE  ceragon
      VARIABLES  {gnGenCfgTrapSeverity , gnGenCfgAlarmText , gnOduStatusFahrenheitTemp,gnGenCfgCLLI}
      DESCRIPTION
          "This Trap is sent every time a Remote ODU returns to normal temperature."
      ::= 314

gnRIDUPowerOkTrap TRAP-TYPE
      ENTERPRISE  ceragon
      VARIABLES  {gnGenCfgTrapSeverity , gnGenCfgAlarmText , gnGenStatDevicePowerSupply,gnGenCfgCLLI}
      DESCRIPTION
          "This Trap is sent every time a Remote IDU Power fault is cleared."
      ::= 315


gnRCableOkTrap TRAP-TYPE
      ENTERPRISE  ceragon
      VARIABLES  {gnGenCfgTrapSeverity , gnGenCfgAlarmText , gnGenStatDeviceCable,gnGenCfgCLLI}
      DESCRIPTION
          "This Trap is sent every time a Remote IDU-ODU cable fault is cleared."
      ::= 316

gnRModemOkTrap TRAP-TYPE
      ENTERPRISE  ceragon
      VARIABLES  {gnGenCfgTrapSeverity , gnGenCfgAlarmText , gnGenCfgCLLI}
      DESCRIPTION
          "This Trap is sent every time a Remote Modem faults is cleared."
      ::= 317


gnRIDUNormalTempTrap TRAP-TYPE
      ENTERPRISE  ceragon
      VARIABLES  {gnGenCfgTrapSeverity , gnGenCfgAlarmText , gnGenStatDeviceFahrenheitTemp,gnGenCfgCLLI}
      DESCRIPTION
          "This Trap is sent every time a Remote IDU returns to normal temperature."
      ::= 318

gnRLoopbackOffTrap TRAP-TYPE
      ENTERPRISE  ceragon
      VARIABLES  {gnGenCfgTrapSeverity , gnGenCfgAlarmText , gnGenCfgCLLI}
      DESCRIPTION
          "This Trap is sent every time a Remote Loopback is cleared."
      ::=  319

gnRRemoteCommOkTrap TRAP-TYPE
      ENTERPRISE  ceragon
      VARIABLES  {gnGenCfgTrapSeverity , gnGenCfgAlarmText , gnGenCfgCLLI}
      DESCRIPTION
          "This Trap is sent every time the remote communication is re-connected."
      ::=  320

gnRNoTestRunningTrap TRAP-TYPE
      ENTERPRISE  ceragon
      VARIABLES  {gnGenCfgTrapSeverity , gnGenCfgAlarmText , gnRstCfgTestActivate,gnGenCfgCLLI}
      DESCRIPTION
          "This Trap is sent every time a Remote SDH/SONET test is cleared."
      ::=  321

gnRNoLOFTrap TRAP-TYPE
      ENTERPRISE  ceragon
      VARIABLES  {ifIndex, gnGenCfgTrapSeverity , gnGenCfgAlarmText , gnGenCfgCLLI}
      DESCRIPTION
          "This Trap is sent every time a Remote Loss of Frame alarm is cleared."
      ::= 322

gnRNoLOSTrap TRAP-TYPE
      ENTERPRISE  ceragon
      VARIABLES  {ifIndex, gnGenCfgTrapSeverity , gnGenCfgAlarmText , gnGenCfgCLLI}
      DESCRIPTION
          "This Trap is sent every time a Remote Loss of Signal alarm is cleared."
      ::= 323

gnRNoTIMTrap TRAP-TYPE
      ENTERPRISE  ceragon
      VARIABLES  {ifIndex, gnGenCfgTrapSeverity , gnGenCfgAlarmText , gnGenCfgCLLI}
      DESCRIPTION
          "This Trap is sent every time a Remote Trace Identifier Mismatch alarm is cleared."
      ::= 324

gnRNoEXCTrap TRAP-TYPE
      ENTERPRISE  ceragon
      VARIABLES  {ifIndex, gnGenCfgTrapSeverity , gnGenCfgAlarmText , gnRstStatBERCur,gnGenCfgCLLI}
      DESCRIPTION
          "This Trap is sent every time a Remote Excessive BER alarm is cleared."
      ::=  325

gnRNoSDTrap TRAP-TYPE
      ENTERPRISE  ceragon
      VARIABLES  {ifIndex, gnGenCfgTrapSeverity , gnGenCfgAlarmText , gnRstStatBERCur,gnGenCfgCLLI}
      DESCRIPTION
          "This Trap is sent every time a Remote Signal Degrade alarm is cleared."
      ::=  326


gnRNoAisTrap TRAP-TYPE
      ENTERPRISE  ceragon
      VARIABLES  {ifIndex, gnGenCfgTrapSeverity , gnGenCfgAlarmText , gnGenCfgCLLI}
      DESCRIPTION
          "This Trap is sent every time the Remote terminal stops receiving an Alarm Indication Signal (AIS)."
      ::=  327

gnRNoUnExpTrap TRAP-TYPE
      ENTERPRISE  ceragon
      VARIABLES  {ifIndex, gnGenCfgTrapSeverity , gnGenCfgAlarmText , gnGenCfgCLLI}
      DESCRIPTION
          "This Trap is sent every time a Remote terminal stops receiving an unexpected signal."
      ::=  328

gnRNoLocTrap TRAP-TYPE
      ENTERPRISE  ceragon
      VARIABLES  {ifIndex, gnGenCfgTrapSeverity , gnGenCfgAlarmText , gnGenCfgCLLI}
      DESCRIPTION
          "This Trap is sent every time a Remote Loss of Carrier (on the FE interfaces) alarm is cleared."
      ::=  329

---
gnRNoLopTrap TRAP-TYPE
      ENTERPRISE  ceragon
      VARIABLES  {ifIndex, gnGenCfgTrapSeverity , gnGenCfgAlarmText , gnGenCfgCLLI}
      DESCRIPTION
          "This Trap is sent every time a Remote Loss of pointer alarm is cleared."
      ::= 	330

gnRNoRdiTrap TRAP-TYPE
      ENTERPRISE  ceragon
      VARIABLES  {ifIndex, gnGenCfgTrapSeverity , gnGenCfgAlarmText , gnGenCfgCLLI}
      DESCRIPTION
          "This Trap is sent every time the Remote terminal stops receiving a Remote Defect Identifier signal (RDI)."
      ::= 	331

gnRNoSlmTrap TRAP-TYPE
      ENTERPRISE  ceragon
      VARIABLES  {ifIndex, gnGenCfgTrapSeverity , gnGenCfgAlarmText , gnGenCfgCLLI}
      DESCRIPTION
          "This Trap is sent every time a Remote Signal (Payload) Label Mismatch alarm is cleared."
      ::= 	332

gnRNoUnqTrap TRAP-TYPE
      ENTERPRISE  ceragon
      VARIABLES  {ifIndex, gnGenCfgTrapSeverity , gnGenCfgAlarmText , gnGenCfgCLLI}
      DESCRIPTION
          "This Trap is sent every time a Remote terminal start receiving an equipped signal."
      ::= 	333

---

gnRExternalAlarm1OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 1 is cleared."
      ::= 334

gnRExternalAlarm2OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 2 is cleared."
      ::= 335

gnRExternalAlarm3OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 3 is cleared."
      ::= 336

gnRExternalAlarm4OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 4 is cleared."
      ::= 337

gnRExternalAlarm5OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 5 is cleared."
      ::= 338

gnRExternalAlarm6OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 6 is cleared."
      ::= 339

gnRExternalAlarm7OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 7 is cleared."
      ::= 340

gnRExternalAlarm8OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 8 is cleared."
      ::= 341

gnRSystemOkTrap TRAP-TYPE
      ENTERPRISE  ceragon
      VARIABLES  {gnGenCfgTrapSeverity , gnGenCfgAlarmText , gnGenStatInternalCommunication,gnGenCfgCLLI}
      DESCRIPTION
          "This Trap is sent every time a Remote System fault is cleared."
      ::= 342

gnRTftpOkTrap TRAP-TYPE
      ENTERPRISE  ceragon
      VARIABLES  {gnGenCfgTrapSeverity , gnGenCfgAlarmText , gnGenCfgCLLI}
      DESCRIPTION
          "This Trap is sent every time a Remote TFTP Download succeeded."
      ::= 343

gnRInternalDownloadOkTrap TRAP-TYPE
      ENTERPRISE  ceragon
      VARIABLES  {gnGenCfgTrapSeverity , gnGenCfgAlarmText , gnGenCfgCLLI}
      DESCRIPTION
          "This Trap is sent every time a Remoteinternal Download succeeded."
      ::= 344

gnRIntralinkOkTrap TRAP-TYPE
      ENTERPRISE  ceragon
      VARIABLES  {gnGenCfgTrapSeverity , gnGenCfgAlarmText , gnGenCfgCLLI}
      DESCRIPTION
          "This Trap is sent every time a Remote intra-link download succeeded."
      ::= 345

gnRNoConfMismatchTrap TRAP-TYPE
      ENTERPRISE  ceragon
      VARIABLES  {gnGenCfgTrapSeverity , gnGenCfgAlarmText , gnGenCfgCLLI}
      DESCRIPTION
          "This Trap is sent every time a Remote configuration mismatch fault is cleared."
      ::= 346

-- "positive" traps are not being send when protection switch occurs.
-- gnRProtectSwitchOkTrap TRAP-TYPE
--     ENTERPRISE  ceragon
--     VARIABLES  {gnGenCfgTrapSeverity , gnGenCfgAlarmText , gnGenCfgCLLI}
--     DESCRIPTION
--        "Never sent."
--     ::= 347

gnRProtectCableOkTrap TRAP-TYPE
      ENTERPRISE  ceragon
      VARIABLES  {gnGenCfgTrapSeverity , gnGenCfgAlarmText , gnGenCfgCLLI}
      DESCRIPTION
          "This Trap is sent every time a Remote protection cable fault is cleared."
      ::= 348

gnRLomOkTrap TRAP-TYPE
      ENTERPRISE  ceragon
      VARIABLES  {ifIndex, gnGenCfgTrapSeverity , gnGenCfgAlarmText , gnGenCfgCLLI}
      DESCRIPTION
          "This Trap is sent every time a Remote Loss of Multi-frame alarm is cleared."
      ::= 350

--gnRHitlessProblemOKTrap TRAP-TYPE
--      ENTERPRISE  ceragon
--      VARIABLES  {gnGenCfgTrapSeverity , gnGenCfgAlarmText , gnGenCfgCLLI}
--      DESCRIPTION
--          "This Trap is sent every time a Remote Hitless fault is cleared."
--      ::= 351

gnRHitlessRadioLofOKTrap TRAP-TYPE
      ENTERPRISE  ceragon
      VARIABLES  {gnGenCfgTrapSeverity , gnGenCfgAlarmText , gnGenCfgCLLI}
      DESCRIPTION
          "This Trap is sent every time a Remote Hitless RadioLOF fault is cleared."
      ::= 352

gnRHitlessCableDisconnectOKTrap	TRAP-TYPE
      ENTERPRISE  ceragon
      VARIABLES  {gnGenCfgTrapSeverity , gnGenCfgAlarmText , gnGenCfgCLLI}
      DESCRIPTION
          "This Trap is sent every time a Remote Hitless cable fault is cleared."
      ::= 353

-- 		skip 354-356 	(MSP PAM, SCM, INV)
-- 		skip 357 		(Inband)

-- Traps #400-600 are reserved for Managment.

END
