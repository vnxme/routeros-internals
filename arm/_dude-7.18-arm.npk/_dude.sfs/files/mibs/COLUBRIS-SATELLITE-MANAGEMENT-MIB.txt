-- *****************************************************************
-- COLUBRIS-SATELLITE-MANAGEMENT-MIB.my: Colubris Networks Satellite
-- Management MIB file
--
-- December 2001
--
-- Copyright (c) 2001, 2002  by Colubris Networks, Inc.
-- All rights reserved.
-- *****************************************************************

COLUBRIS-SATELLITE-MANAGEMENT-MIB DEFINITIONS ::= BEGIN

IMPORTS
	MODULE-IDENTITY,
	OBJECT-TYPE,
	NOTIFICATION-TYPE,
	IpAddress
		FROM SNMPv2-SMI
	TEXTUAL-CONVENTION, 
	MacAddress,
	DisplayString
		FROM SNMPv2-TC
	MODULE-COMPLIANCE,
	OBJECT-GROUP
		FROM SNMPv2-CONF
	colubrisMgmt
		FROM COLUBRIS-SMI;

colubrisSatelliteManagementMIB  MODULE-IDENTITY
	LAST-UPDATED "200112110000Z"
	ORGANIZATION "Colubris Networks, Inc."
	CONTACT-INFO
		"	Colubris Networks
			Customer Service

		Postal: 420 Armand-Frappier, Suite 200
			Laval, QC  H7V 4B4
			CANADA

		   Tel: +1 450 680-1661

		E-mail: cn-snmp@colubris.com"
	DESCRIPTION
		"Initial version of Colubris SatelliteManagement MIB module."
	::= { colubrisMgmt 7 }

-- colubrisSatelliteManagementMIB definition

colubrisSatelliteManagementMIBObjects OBJECT IDENTIFIER ::= { colubrisSatelliteManagementMIB 1 }

-- MIB defines the following groupings
satelliteInfo OBJECT IDENTIFIER ::= { colubrisSatelliteManagementMIBObjects 1 }
masterSettings OBJECT IDENTIFIER ::= { colubrisSatelliteManagementMIBObjects 2 }

satelliteTable OBJECT-TYPE
	SYNTAX SEQUENCE OF SatelliteEntry
	MAX-ACCESS	not-accessible
	STATUS		current
	DESCRIPTION
		"The table of all Satellite access points
		 currently registered by the Master access
		 point."
	INDEX { satelliteIndex }
	::=   { satelliteInfo 1 }

satelliteEntry OBJECT-TYPE
	SYNTAX	SatelliteEntry
	MAX-ACCESS	not-accessible
	STATUS	current
	DESCRIPTION
		"Information about a Satellite access point
		 currently registered by the Master access point."
	INDEX { satelliteIndex }
	::=   { satelliteTable 1 }

SatelliteEntry ::= SEQUENCE
{
	satelliteIndex
			INTEGER,
	satelliteDeviceId
			DisplayString,
	satelliteMacAddress
			MacAddress,
	satelliteIpAddress
			IpAddress,
	satelliteName
			DisplayString,
	satelliteESSID
			DisplayString,
	satelliteChannelNumber
			INTEGER,
	satelliteForwardWirelessToWireless
			INTEGER,
	satelliteMasterTrafficOnly
			INTEGER,
	satelliteSNMPPort
			INTEGER,
	satelliteSecureWebPort
			INTEGER
}

satelliteIndex OBJECT-TYPE
	SYNTAX		INTEGER
	MAX-ACCESS	read-only
	STATUS		current
	DESCRIPTION
		"Index of a the satellite in the satelliteTable."
	::= { satelliteEntry 1 }

satelliteDeviceId OBJECT-TYPE
	SYNTAX		DisplayString
	MAX-ACCESS	read-only
	STATUS		current
	DESCRIPTION
		"Device ID of a the satellite in the satelliteTable."
	::= { satelliteEntry 2 }

satelliteMacAddress OBJECT-TYPE
	SYNTAX		MacAddress
	MAX-ACCESS	read-only
	STATUS		current
	DESCRIPTION
		"Indicates the MAC address of the Satellite access point."
	::= { satelliteEntry 3 }

satelliteIpAddress OBJECT-TYPE
	SYNTAX		IpAddress
	MAX-ACCESS	read-only
	STATUS		current
	DESCRIPTION
		"Specifies the IP address of the Satellite access point."
	::= { satelliteEntry 4 }

satelliteName OBJECT-TYPE
	SYNTAX		DisplayString
	MAX-ACCESS	read-only
	STATUS		current
	DESCRIPTION
		"Specifies the name of the Satellite access point."
	::= { satelliteEntry 5 }

satelliteESSID OBJECT-TYPE
	SYNTAX		DisplayString
	MAX-ACCESS	read-only
	STATUS		current
	DESCRIPTION
		"Specifies the ESSID of the Satellite access point."
	::= { satelliteEntry 6 }

satelliteChannelNumber OBJECT-TYPE
	SYNTAX		INTEGER
	MAX-ACCESS	read-only
	STATUS		current
	DESCRIPTION
		"Specifies the wireless channel number the Satellite
		 access point is operating on."
	::= { satelliteEntry 7 }

satelliteForwardWirelessToWireless OBJECT-TYPE
	SYNTAX		INTEGER
	{
		enable(1),
		disable(2)
	}
	MAX-ACCESS	read-only
	STATUS		current
	DESCRIPTION
		"Specifies if the forwarding of traffic between 
		 wireless client stations is enabled on the Satellite
		 access point."
	::= { satelliteEntry 8 }

satelliteMasterTrafficOnly	OBJECT-TYPE
	SYNTAX		INTEGER
	{
		enable(1),
		disable(2)
	}
	MAX-ACCESS	read-only
	STATUS		current
	DESCRIPTION
		"Specifies if the Satellite will only forward traffic that
		 is addressed to the MAC address of the Master 
		 access point."
	::= { satelliteEntry 9 }

satelliteSNMPPort	OBJECT-TYPE
	SYNTAX		INTEGER
	MAX-ACCESS	read-only
	STATUS		current
	DESCRIPTION
		"Specifies the SNMP port on which the Satellite listens."
	::= { satelliteEntry 10 }

satelliteSecureWebPort	OBJECT-TYPE
	SYNTAX		INTEGER
	MAX-ACCESS	read-only
	STATUS		current
	DESCRIPTION
		"Specifies the secure web port on which the satellite listens."
	::= { satelliteEntry 11 }

satelliteUpNotificationEnabled OBJECT-TYPE 
	SYNTAX	INTEGER
	{
		disabled(0),
		enabled(1)
	}
	MAX-ACCESS	read-write
	STATUS	current
	DESCRIPTION
		"Specifies if satelliteUpNotification notifications will be sent."
	DEFVAL	{ enabled }
	::= { masterSettings 1 }

satelliteDownNotificationEnabled OBJECT-TYPE 
	SYNTAX	INTEGER
	{
		disabled(0),
		enabled(1)
	}
	MAX-ACCESS	read-write
	STATUS	current
	DESCRIPTION
		"Specifies if satelliteDownNotification notifications will be sent."
	DEFVAL	{ enabled }
	::= { masterSettings 2 }

-- notifications
	
colubrisSatelliteManagementMIBNotificationPrefix OBJECT IDENTIFIER
	 ::= { colubrisSatelliteManagementMIB 2 }
colubrisSatelliteManagementMIBNotifications OBJECT IDENTIFIER
	 ::= {colubrisSatelliteManagementMIBNotificationPrefix 0  }
		
satelliteUpNotification NOTIFICATION-TYPE
	OBJECTS
	{
		satelliteName,
		satelliteDeviceId,
		satelliteMacAddress,
		satelliteIpAddress,
		satelliteESSID
	}
	STATUS	current
	DESCRIPTION
		"Sent when a new satellite is detected." 
  --#SUMMARY "New satellite detected: name:%s IP:%s MAC:%m ESSID:%s ID:%s"
  --#ARGUMENTS { 0, 1, 2, 3, 4 }
  --#SEVERITY INFORMATIONNAL
  --#CATEGORY "Colubris Networks Alarms"
	::= { colubrisSatelliteManagementMIBNotifications  1 }

satelliteDownNotification NOTIFICATION-TYPE
	OBJECTS
	{
                satelliteName,
                satelliteDeviceId,
                satelliteMacAddress,
                satelliteIpAddress,
                satelliteESSID										
	}
	STATUS	current
	DESCRIPTION
		"Sent when a satellite becomes unreachable."
  --#SUMMARY "Satellite unreachable: name:%s IP:%s MAC:%m ESSID:%s ID:%s"
  --#ARGUMENTS { 0, 1, 2, 3, 4 }
  --#SEVERITY INFORMATIONNAL
  --#CATEGORY "Colubris Networks Alarms"
	::= { colubrisSatelliteManagementMIBNotifications 2 }

-- conformance information

colubrisSatelliteManagementMIBConformance OBJECT IDENTIFIER ::= { colubrisSatelliteManagementMIB 3 }
colubrisSatelliteManagementMIBCompliances OBJECT IDENTIFIER ::= { colubrisSatelliteManagementMIBConformance 1 }
colubrisSatelliteManagementMIBGroups      OBJECT IDENTIFIER ::= { colubrisSatelliteManagementMIBConformance 2 }

-- compliance statements     

colubrisSatelliteManagementMIBCompliance MODULE-COMPLIANCE
	STATUS current
	DESCRIPTION
		"The compliance statement for entities which implement
		 the Colubris SatelliteManagement MIB."
	MODULE
		MANDATORY-GROUPS
		{
			colubrisSatelliteManagementMIBGroup
		}
	::= { colubrisSatelliteManagementMIBCompliances 1 }

-- units of conformance

colubrisSatelliteManagementMIBGroup OBJECT-GROUP
	OBJECTS
	{
		satelliteIndex,
		satelliteDeviceId,
		satelliteMacAddress,
		satelliteIpAddress,
		satelliteName,
		satelliteESSID,
		satelliteChannelNumber,
		satelliteForwardWirelessToWireless,
		satelliteMasterTrafficOnly,
		satelliteSNMPPort,
		satelliteSecureWebPort,
		satelliteUpNotificationEnabled,
		satelliteDownNotificationEnabled
	}
	STATUS current
	DESCRIPTION
		"A collection of objects providing the Satellite Management MIB capability."
	::= { colubrisSatelliteManagementMIBGroups 1 }

END
