-- *****************************************************************
-- COLUBRIS-CDP-MIB.my:  Colubris CDP MIB file
--
-- January 2002
--
-- Copyright (c) 2002  by Colubris Networks, Inc.
-- All rights reserved.
-- *****************************************************************

COLUBRIS-CDP-MIB DEFINITIONS ::= BEGIN

IMPORTS
        MODULE-IDENTITY,
        OBJECT-TYPE
		FROM SNMPv2-SMI
	DisplayString,
	MacAddress
		FROM SNMPv2-TC
	MODULE-COMPLIANCE,
	OBJECT-GROUP
		FROM SNMPv2-CONF
	colubrisMgmt
		FROM COLUBRIS-SMI;

colubrisCdpMIB   MODULE-IDENTITY
	LAST-UPDATED "200202270000Z"
	ORGANIZATION "Colubris Networks, Inc."
	CONTACT-INFO
		"	Colubris Networks
			Customer Service

		Postal: 420 Armand-Frappier, Suite 200
			Laval, QC  H7V 4B4
			CANADA

		   Tel: +1 450 680-1661

		E-mail: cn-snmp@colubris.com"
	DESCRIPTION
		"Initial version of Colubris CDP MIB module."
	::= { colubrisMgmt 9 }


colubrisCdpMIBObjects OBJECT IDENTIFIER ::= { colubrisCdpMIB 1 }

coCdpCache     OBJECT IDENTIFIER ::= { colubrisCdpMIBObjects 1 }
coCdpGlobal    OBJECT IDENTIFIER ::= { colubrisCdpMIBObjects 2 }

--
-- The CDP Address Cache Group
--

coCdpCacheTable OBJECT-TYPE
    SYNTAX     SEQUENCE OF CoCdpCacheEntry
    MAX-ACCESS not-accessible
    STATUS     current
    DESCRIPTION
            "The (conceptual) table containing the cached
            information obtained via receiving CDP messages."
    ::= { coCdpCache 1 }

coCdpCacheEntry OBJECT-TYPE
    SYNTAX     CoCdpCacheEntry
    MAX-ACCESS not-accessible
    STATUS     current
    DESCRIPTION
            "An entry (conceptual row) in the coCdpCacheTable,
            containing the information received via CDP on one
            interface from one device.  Entries appear when
            a CDP advertisement is received from a neighbor
            device."
    INDEX      { coCdpCacheDeviceIndex }
    ::= { coCdpCacheTable 1 }

CoCdpCacheEntry ::= SEQUENCE {
    coCdpCacheDeviceIndex             INTEGER,
    coCdpCacheLocalInterface          DisplayString,
    coCdpCacheAddress                 MacAddress,
    coCdpCacheDeviceId                DisplayString,
    coCdpCacheTimeToLive              INTEGER,
    coCdpCacheCapabilities            DisplayString,
    coCdpCacheVersion                 DisplayString,
    coCdpCachePlatform                DisplayString,
    coCdpCachePortId                  DisplayString
}

coCdpCacheDeviceIndex OBJECT-TYPE
    SYNTAX     INTEGER (1..50)
    MAX-ACCESS not-accessible
    STATUS     current
    DESCRIPTION
            "A unique value for each device from which CDP messages
            are being received."
    ::= { coCdpCacheEntry 1 }

coCdpCacheLocalInterface OBJECT-TYPE
    SYNTAX     DisplayString
    MAX-ACCESS read-only
    STATUS     current
    DESCRIPTION
            "The interface name which received the recent CDP
	    message."
    ::= { coCdpCacheEntry 2 }

coCdpCacheAddress OBJECT-TYPE
    SYNTAX     MacAddress
    MAX-ACCESS read-only
    STATUS     current
    DESCRIPTION
            "The ethernet address of the device."
    ::= { coCdpCacheEntry 3 }

coCdpCacheDeviceId OBJECT-TYPE
    SYNTAX     DisplayString
    MAX-ACCESS read-only
    STATUS     current
    DESCRIPTION
            "The Device-ID string as reported in the most recent CDP
            message.  The zero-length string indicates no Device-ID
            field (TLV) was reported in the most recent CDP
            message."
    ::= { coCdpCacheEntry 4 }

coCdpCacheTimeToLive OBJECT-TYPE
    SYNTAX     INTEGER
    MAX-ACCESS read-only
    STATUS     current
    DESCRIPTION
	    "The number of seconds to keep the remote device in the
	    cache table after receiving the CDP message."
    ::= { coCdpCacheEntry 5 }

coCdpCacheCapabilities OBJECT-TYPE
    SYNTAX     DisplayString
    MAX-ACCESS read-only
    STATUS     current
    DESCRIPTION
            "The Device's Functional Capabilities as reported in the
            most recent CDP message. Possible values are:
		R - layer 3 router
		T - a layer 2 transparent bridge 
		B - a layer 2 source-root bridge
		S - a layer 2 switch (non-spanning tree)
		r - a layer 3 (non routing) host
		I - does not forward IGMP Packets to non-routers
		H - a layer 1 repeater
            The zero-length string indicates no Capabilities field
            (TLV) was reported in the most recent CDP message."
    ::= { coCdpCacheEntry 6 }

coCdpCacheVersion OBJECT-TYPE
    SYNTAX     DisplayString
    MAX-ACCESS read-only
    STATUS     current
    DESCRIPTION
            "The Version string as reported in the most recent CDP
            message.  The zero-length string indicates no Version
            field (TLV) was reported in the most recent CDP
            message."
    ::= { coCdpCacheEntry 7 }

coCdpCachePlatform OBJECT-TYPE
    SYNTAX     DisplayString
    MAX-ACCESS read-only
    STATUS     current
    DESCRIPTION
            "The Device's Hardware Platform as reported in the most
            recent CDP message.  The zero-length string indicates
            that no Platform field (TLV) was reported in the most
            recent CDP message."
    ::= { coCdpCacheEntry 8 }

coCdpCachePortId OBJECT-TYPE
    SYNTAX     DisplayString
    MAX-ACCESS read-only
    STATUS     current
    DESCRIPTION
            "The Port-ID string as reported in the most recent CDP
            message.  This will typically be the value of the ifName
            object (e.g., 'Ethernet0').  The zero-length string
            indicates no Port-ID field (TLV) was reported in the
            most recent CDP message."
    ::= { coCdpCacheEntry 9 }

coCdpGlobalMessageInterval OBJECT-TYPE
    SYNTAX     INTEGER (5..254)
    UNITS      "seconds"
    MAX-ACCESS read-write
    STATUS     current
    DESCRIPTION
            "The interval at which CDP messages are to be generated.
            The default value is 60 seconds."
    DEFVAL     { 60 }
    ::= { coCdpGlobal 1 }

coCdpGlobalHoldTime OBJECT-TYPE
    SYNTAX     INTEGER (10..255)
    UNITS      "seconds"
    MAX-ACCESS read-write
    STATUS     current
    DESCRIPTION
            "The time the receiving device holds CDP message.
            The default value is 180 seconds."
    DEFVAL     { 180 }
    ::= { coCdpGlobal 2 }

-- conformance information

colubrisCdpMIBConformance
              OBJECT IDENTIFIER ::= { colubrisCdpMIB 2 }
colubrisCdpMIBCompliances
              OBJECT IDENTIFIER ::= { colubrisCdpMIBConformance 1 }
colubrisCdpMIBGroups
              OBJECT IDENTIFIER ::= { colubrisCdpMIBConformance 2 }

-- compliance statements

colubrisCdpMIBCompliance MODULE-COMPLIANCE
    STATUS  current 
    DESCRIPTION
            "The compliance statement for the CDP MIB."
    MODULE  -- this module
        MANDATORY-GROUPS { colubrisCdpMIBGroup }
 
    ::= { colubrisCdpMIBCompliances 1 }

-- units of conformance

colubrisCdpMIBGroup OBJECT-GROUP
    OBJECTS { coCdpCacheLocalInterface, 
    	      coCdpCacheAddress, coCdpCacheDeviceId,
	      coCdpCacheTimeToLive, coCdpCacheCapabilities,
	      coCdpCacheVersion, coCdpCachePlatform,
	      coCdpCachePortId, coCdpGlobalMessageInterval,
	      coCdpGlobalHoldTime
	    }
    STATUS  current
    DESCRIPTION
            "A collection of objects for use with CDP."
    ::= { colubrisCdpMIBGroups 1 }

END
