-- Private MIB definition for Trango Systems
-- Access 2400 series wireless broadband Access Point M2400S-AP
-- Version: 1.1
-- Date: October 07, 2004
--
-- Copyright 2003: Trango Systems, Inc. All Rights Reserved.
-- Trango Systems, Inc. 15070 Avenue Of Science Suite 200 San Diego CA 92128 USA.
--
-- Reproduction of this document is authorized on condition that the
-- foregoing copyright notice is included.

TRANGOM2400S-MIB DEFINITIONS ::= BEGIN

-- MIB module for enterprise trango wireless broadband
-- of management of M2400S AP and SU units

	IMPORTS
        	enterprises, IpAddress, Counter
            		FROM RFC1155-SMI
        	TRAP-TYPE
            		FROM RFC-1215
	        OBJECT-TYPE
        		FROM RFC-1212;

	-- textual conventions

	DisplayString ::=
        OCTET STRING
            	-- This data type is used to model textual information taken
		-- from the NVT ASCII character set.  By convention, objects
            	-- with this syntax are declared as having
            	--
            	-- SIZE (0..255)


	-- trango wireless broadband MIB registration id assigned to 5454.
        -- customer needs to change this value based on their OEM value.
	trango		OBJECT IDENTIFIER ::= { enterprises 5454 }
	tbw	        OBJECT IDENTIFIER ::= { trango 1 }
	m2400sap	OBJECT IDENTIFIER ::= { tbw 32 }

	-- modules branched from m2400sap
	apsystem	OBJECT IDENTIFIER ::= { m2400sap 1 }
	aprf	    	OBJECT IDENTIFIER ::= { m2400sap 2 }
	su  	    	OBJECT IDENTIFIER ::= { m2400sap 3 }
	trapconfig  	OBJECT IDENTIFIER ::= { m2400sap 4 }
	mibinfo   	OBJECT IDENTIFIER ::= { m2400sap 5 }
    	m2400straps	OBJECT IDENTIFIER ::= { m2400sap 16}
    
	apversion	OBJECT IDENTIFIER ::= { apsystem 1 }
	apswitches	OBJECT IDENTIFIER ::= { apsystem 13}
	aptraffic	OBJECT IDENTIFIER ::= { apsystem 15}
	apipconfig	OBJECT IDENTIFIER ::= { apsystem 18}
	aprftable   	OBJECT IDENTIFIER ::= { aprf 3 }
        sudb        	OBJECT IDENTIFIER ::= { su 4 }

	-- MIB objects defined below

	-- apsystem objects
	apversionHW	OBJECT-TYPE
		SYNTAX	DisplayString (SIZE (0..4))
            	ACCESS 	read-only
            	STATUS 	mandatory
	        DESCRIPTION
	    		"Hardware version."
            	::= { apversion 1 }

	apversionFW OBJECT-TYPE
            	SYNTAX	DisplayString (SIZE (0..80))
            	ACCESS 	read-only
            	STATUS 	mandatory
            	DESCRIPTION
	        	"Main firmware version.
                 	 Format: <code version>H<hardware version>D<date>."
            	::= { apversion 2 }

	apversionFWChecksum OBJECT-TYPE
		SYNTAX	DisplayString (SIZE (0..8))
            	ACCESS 	read-only
            	STATUS 	mandatory
            	DESCRIPTION
	    		"AP firmware checksum."
            	::= { apversion 3 }

	apversionFPGA OBJECT-TYPE
		SYNTAX	DisplayString (SIZE (0..8))
            	ACCESS 	read-only
            	STATUS 	mandatory
            	DESCRIPTION
	    		"FPGA firmware version."
            	::= { apversion 4 }

	apversionFPGAChecksum OBJECT-TYPE
		SYNTAX	DisplayString (SIZE (0..8))
            	ACCESS 	read-only
            	STATUS 	mandatory
            	DESCRIPTION
	    		"AP FPGA firmware checksum."
            	::= { apversion 5 }

	apsystemDeviceId OBJECT-TYPE
	    	SYNTAX 	OCTET STRING (SIZE(6))
	    	ACCESS 	read-only
	    	STATUS 	mandatory
	    	DESCRIPTION
			"MAC address."
	    	::= { apsystem 2 }

	apsystemBaseId OBJECT-TYPE
	        SYNTAX  DisplayString (SIZE (0..4))
	    	ACCESS 	read-write
	    	STATUS 	mandatory
	    	DESCRIPTION
			"Cluster that the AP belongs to.
                 	 All APs and SUs in the same cluster shall have the same Base ID."
	    	::= { apsystem 3 }

	apsystemAPId OBJECT-TYPE
	    	SYNTAX	OCTET STRING (SIZE(1))
	    	ACCESS 	read-write
	    	STATUS 	mandatory
	    	DESCRIPTION
			"AP ID. Each AP in a cluster shall have unique AP ID."
	    	::= { apsystem 4 }

	apsystemDefOpMode OBJECT-TYPE
	    	SYNTAX	INTEGER {
                	on(0),
                       	off(255)
                  	}
	    	ACCESS 	read-write
	    	STATUS 	mandatory
	    	DESCRIPTION
			"The operation mode (on or off) the radio is on after reboot/power cycle."
	    	::= { apsystem 5 }

	apsystemCurOpMode OBJECT-TYPE
	    	SYNTAX	INTEGER {
                       	on(0),
                       	off(255)
                   	}
	    	ACCESS 	read-only
	    	STATUS 	mandatory
	    	DESCRIPTION
			"Radio's current operation mode."
	    	::= { apsystem 6 }
        
    	apsystemActivateOpmode OBJECT-TYPE
            	SYNTAX	INTEGER {
	        	deactivated(0),
                       	activateapmode(1)
                   	}
            	ACCESS 	read-write
            	STATUS  mandatory
            	DESCRIPTION
                	"Engage AP unit to ap operation mode."
            	DEFVAL	{ deactivated }
            	::= { apsystem 7 }

	apsystemIpAddr OBJECT-TYPE
		SYNTAX 	IpAddress
		ACCESS 	read-only
		STATUS 	mandatory
		DESCRIPTION
			"Current IP address."
		::= { apsystem 8 }

    	apsystemSubnet OBJECT-TYPE
		SYNTAX	IpAddress
		ACCESS	read-only
		STATUS	mandatory
		DESCRIPTION
			"Current Subnet mask."
		::= { apsystem 9 }

	apsystemDefaultGateway OBJECT-TYPE
		SYNTAX	IpAddress
		ACCESS	read-only
		STATUS	mandatory
		DESCRIPTION
			"Current Default gateway."
		::= { apsystem 10 }

	apsystemReadCommStr OBJECT-TYPE
        	SYNTAX  DisplayString (SIZE (0..32))
		ACCESS	read-write
		STATUS  mandatory
		DESCRIPTION
			"SNMP agent read community string. It is used for authentication purpose."
		::= { apsystem 11 }

	apsystemWriteCommStr OBJECT-TYPE
	        SYNTAX  DisplayString (SIZE (0..32))
		ACCESS	read-write
		STATUS  mandatory
		DESCRIPTION
			"SNMP agent write community string. It is used for authentication purpose."
		::= { apsystem 12 }

	apswitchesBlockBroadcastMulticast OBJECT-TYPE
		SYNTAX	INTEGER {
	        	passed(0),
        	        blocked(1)
                	}
		ACCESS 	read-write
		STATUS 	mandatory
		DESCRIPTION
			"This switch enables or disables the blocking of Ethernet
		         control packet except ICMP and ARP to reduce the amount
	                 of uneccessary overhead introduced to the wireless link."
		DEFVAL	{ blocked }
		::= { apswitches 1 }

	apswitchesSUtoSU OBJECT-TYPE
 		SYNTAX	INTEGER {
                        disabled(0),
                        enabled(1)
                        }
		ACCESS 	read-write
		STATUS 	mandatory
		DESCRIPTION
			"This switch enables or disables the peer-to-peer
        	         feature among SUs through the AP. Before this switch
                         is turned on, all SUs that want to communicate with
                         each other have to be assigned to the same group."
		DEFVAL	{ disabled }
		::= { apswitches 2 }

	apswitchesTFTPD OBJECT-TYPE
		SYNTAX	INTEGER {
	                disabled(0),
                        enabled(1)
                	}
		ACCESS 	read-write
		STATUS 	mandatory
		DESCRIPTION
			"This switch enables or disables the TFTP operation. When
	                 it is turned on, then the AP will be ready for code download."
		DEFVAL	{ disabled }
		::= { apswitches 3 }

	apswitchesHTTPD OBJECT-TYPE
		SYNTAX	INTEGER {
                        disabled(0),
                        enabled(1)
                        }
		ACCESS 	read-write
		STATUS 	mandatory
		DESCRIPTION
			"When it is turned on, then the AP is accessible for
                         configuring via web browser (e.g. IE or Nescape)."
		DEFVAL	{ enabled }
		::= { apswitches 4 }

	apswitchesTcpIpServiceForSU OBJECT-TYPE
		SYNTAX	INTEGER {
                        disabled(0),
                        enabled(1)
                        }
		ACCESS 	read-write
		STATUS 	mandatory
		DESCRIPTION
			"It allows TCP/IP access into the AP
			 via the RF link when opmode is on."
		DEFVAL	{ disabled }
		::= { apswitches 5 }

	apsystemMIRThreshold OBJECT-TYPE
		SYNTAX	INTEGER {
                        onembps(1),
                        twombps(2),
                        threembps(3),
                        fourmbps(4),
                        fivembps(5)
                        }
		ACCESS	read-write
		STATUS  mandatory
		DESCRIPTION
			"Maximum Information Rate (in Mbps), the AP allows the
                         network to utilize before enforcing DownLink CIR on each subscriber."
		::= { apsystem 14 }

	aptrafficEthInOctets OBJECT-TYPE
		SYNTAX 	Counter
		ACCESS	read-only
		STATUS	mandatory
		DESCRIPTION
			"Number of payload octets received on Ethernet port."
		::= { aptraffic 1 }

	aptrafficEthOutOctets OBJECT-TYPE
		SYNTAX 	Counter
		ACCESS	read-only
		STATUS	mandatory
		DESCRIPTION
			"Number of payload octets transmitted on Ethernet port."
		::= { aptraffic 2 }

	aptrafficRfInPackets OBJECT-TYPE
		SYNTAX 	Counter
		ACCESS	read-only
		STATUS	mandatory
		DESCRIPTION
			"Number of packets of SUs payload received from RF port."
		::= { aptraffic 3 }

	aptrafficRfOutPackets OBJECT-TYPE
		SYNTAX 	Counter
		ACCESS	read-only
		STATUS	mandatory
		DESCRIPTION
			"Number of packets of SUs payload transmitted to RF port."
		::= { aptraffic 4 }

	aptrafficRfinDropPackets OBJECT-TYPE
		SYNTAX 	Counter
		ACCESS	read-only
		STATUS	mandatory
		DESCRIPTION
			"Number of packets of SUs payload received from RF port."
		::= { aptraffic 5 }

	aptrafficRfInOctets OBJECT-TYPE
		SYNTAX 	Counter
		ACCESS	read-only
		STATUS	mandatory
		DESCRIPTION
			"Number of octets of SUs payload received from RF port."
		::= { aptraffic 6 }

	aptrafficRfOutOctets OBJECT-TYPE
		SYNTAX 	Counter
		ACCESS	read-only
		STATUS	mandatory
		DESCRIPTION
			"Number of octets of SUs payload transmitted to RF port."
		::= { aptraffic 7 }

	apsystemUpdateFlashAndActivate OBJECT-TYPE
		SYNTAX	INTEGER {
                        no(0),
                        yes(1)
                        }
		ACCESS	read-write
		STATUS	mandatory
		DESCRIPTION
			"Save system setting values to Flash and activate the settings."
        	DEFVAL  {no}
		::= { apsystem 16 }

	apsystemReboot OBJECT-TYPE
		SYNTAX	INTEGER {
                        deactivated(0),
                        activated(1)
                        }
		ACCESS	read-write
		STATUS  mandatory
		DESCRIPTION
			"Reboot the radio."
        	DEFVAL { deactivated }
		::= { apsystem 17 }

	apipconfigIpAddress OBJECT-TYPE
		SYNTAX 	IpAddress
		ACCESS 	read-write
		STATUS 	mandatory
		DESCRIPTION
			"New IP address. It will be saved to
                         non-volatile memory and activated in 5 secs."
		::= { apipconfig 1 }

	apipconfigSubnet OBJECT-TYPE
		SYNTAX	IpAddress
		ACCESS	read-write
		STATUS	mandatory
		DESCRIPTION
			"New Subnet mask. It will be saved to
                         non-volatile memory and activated in 5 secs."
		::= { apipconfig 2 }

    	apipconfigDefaultGateway OBJECT-TYPE
		SYNTAX	IpAddress
		ACCESS	read-write
		STATUS	mandatory
		DESCRIPTION
			"New Default gateway. It will be saved to
                         non-volatile memory and activated in 5 secs."
		::= { apipconfig 3 }

	apsystemResetTrafficCounters OBJECT-TYPE
		SYNTAX	INTEGER {
                        deactivated(0),
                        activated(1)
                        }
		ACCESS	read-write
		STATUS  mandatory
		DESCRIPTION
			"Clear the traffic counters."
        	DEFVAL { deactivated }
		::= { apsystem 19 }

	-- aprf objects
	aprfActiveChannel OBJECT-TYPE
		SYNTAX 	INTEGER (1..8)
		ACCESS	read-write
		STATUS	mandatory
		DESCRIPTION
			"It specifies the current channel number the radio operates on."
		::= { aprf 1 }

	aprfActiveAntenna OBJECT-TYPE
                SYNTAX  DisplayString (SIZE (1))
		ACCESS	read-write
		STATUS	mandatory
		DESCRIPTION
			"It specifies the current polarization or antenna the radio operates
			 on. v for vertical polarization, h for horizontal polarization and
			 e for external antenna."
		::= { aprf 2 }

	aprftableChannel1 OBJECT-TYPE
		SYNTAX 	INTEGER (2405..2478)
		ACCESS	read-write
		STATUS	mandatory
		DESCRIPTION
			"RF channel 1 frequency (in MHz). It allows you to create your
	                 own channel instead of the manufacturing defaults in the AP.
                         Keep in mind that channel width is 6MHz, and the frequency
                         specified here is the center frequency."
		::= { aprftable 1 }

	aprftableChannel2 OBJECT-TYPE
		SYNTAX 	INTEGER (2405..2478)
		ACCESS	read-write
		STATUS	mandatory
		DESCRIPTION
			"RF channel 2 frequency (in MHz). It allows you to create your
	                 own channel instead of the manufacturing defaults in the AP.
        	         Keep in mind that channel width is 6MHz, and the frequency
	                 specified here is the center frequency."
		::= { aprftable 2 }

	aprftableChannel3 OBJECT-TYPE
		SYNTAX 	INTEGER (2405..2478)
		ACCESS	read-write
		STATUS	mandatory
		DESCRIPTION
			"RF channel 3 frequency (in MHz). It allows you to create your
	                 own channel instead of the manufacturing defaults in the AP.
	                 Keep in mind that channel width is 6MHz, and the frequency
	                 specified here is the center frequency."
		::= { aprftable 3 }

	aprftableChannel4 OBJECT-TYPE
		SYNTAX 	INTEGER (2405..2478)
		ACCESS	read-write
		STATUS	mandatory
		DESCRIPTION
			"RF channel 4 frequency (in MHz). It allows you to create your
	                 own channel instead of the manufacturing defaults in the AP.
        	         Keep in mind that channel width is 6MHz, and the frequency
	                 specified here is the center frequency."
		::= { aprftable 4 }

	aprftableChannel5 OBJECT-TYPE
		SYNTAX 	INTEGER (2405..2478)
		ACCESS	read-write
		STATUS	mandatory
		DESCRIPTION
			"RF channel 4 frequency (in MHz). It allows you to create your
	                 own channel instead of the manufacturing defaults in the AP.
        	         Keep in mind that channel width is 6MHz, and the frequency
	                 specified here is the center frequency."
		::= { aprftable 5 }

	aprftableChannel6 OBJECT-TYPE
		SYNTAX 	INTEGER (2405..2478)
		ACCESS	read-write
		STATUS	mandatory
		DESCRIPTION
			"RF channel 4 frequency (in MHz). It allows you to create your
	                 own channel instead of the manufacturing defaults in the AP.
        	         Keep in mind that channel width is 6MHz, and the frequency
	                 specified here is the center frequency."
		::= { aprftable 6 }

	aprftableChannel7 OBJECT-TYPE
		SYNTAX 	INTEGER (2405..2478)
		ACCESS	read-write
		STATUS	mandatory
		DESCRIPTION
			"RF channel 4 frequency (in MHz). It allows you to create your
	                 own channel instead of the manufacturing defaults in the AP.
        	         Keep in mind that channel width is 6MHz, and the frequency
	                 specified here is the center frequency."
		::= { aprftable 7 }

	aprftableChannel8 OBJECT-TYPE
		SYNTAX 	INTEGER (2405..2478)
		ACCESS	read-write
		STATUS	mandatory
		DESCRIPTION
			"RF channel 4 frequency (in MHz). It allows you to create your
	                 own channel instead of the manufacturing defaults in the AP.
        	         Keep in mind that channel width is 6MHz, and the frequency
	                 specified here is the center frequency."
		::= { aprftable 8 }

	aprfTxPowerMax OBJECT-TYPE
		SYNTAX 	INTEGER (-128..127)
		ACCESS	read-only
		STATUS	mandatory
		DESCRIPTION
	        	"The maximum Tx power value can be set (in dBm)."
	        ::= { aprf 4 }
    
	aprfTxPowerMin OBJECT-TYPE
		SYNTAX 	INTEGER (-128..127)
		ACCESS	read-only
		STATUS	mandatory
		DESCRIPTION
        	    	"The minimum Tx power value can be set (in dBm)."
	        ::= { aprf 5 }
    
	aprfTxPower OBJECT-TYPE
		SYNTAX 	INTEGER (-128..127)
		ACCESS	read-write
		STATUS	mandatory
		DESCRIPTION
			"RF tx power (in dBm). It specifies the power output
	                 of the radio, excluding the antenna gain. Check parameters
        	         aprfTxPowerMax and apismTxPowerMin for power setting range."
		::= { aprf 6 }

	aprfRxThreshold OBJECT-TYPE
		SYNTAX 	INTEGER	(-98..-55)
		ACCESS	read-write
		STATUS	mandatory
		DESCRIPTION
			"RF rx threshold of the radio(in dBm). The radio will not
			 process the rx signals below this level. It is very useful
			 for interference mitigration. Setting the threshold higher
			 will raise the level of the noise floor the radio can handle
			 but also reduce the range."
		::= { aprf 7 }

	aprfTargetRSSI OBJECT-TYPE
		SYNTAX 	INTEGER (-90..-50)
		ACCESS	read-write
		STATUS	mandatory
		DESCRIPTION
			"RF target RSSI (in dBm). It specifies the target RSSI from all SUs to
	                 the AP. Based on this parameter, the AP can power level each SU
        	         so that it receives same level of signal strength from all SUs,
	                 regardless far or near. Note that when you set the Target RSSI
	                 from SU, you need to consider AP's RF Rx Threshold value.
	                 The Target RSSI from SU must be 5dB higher than the RF Rx Threshold.
	                 When the RF Rx Threshold is disabled, the setting of the Target RSSI
	                 from SU shall be no less than -75dBm."
		::= { aprf 8 }

	-- SU objects
	suSUCount OBJECT-TYPE
 		SYNTAX	INTEGER (0..128)
		ACCESS	read-only
		STATUS	mandatory
		DESCRIPTION
			"Number of subscriber units in the subscriber database."
		::= { su 1 }

    	suStatisticsSamplePeriod OBJECT-TYPE
		SYNTAX	INTEGER (1..60)
	        ACCESS  read-write
        	STATUS  mandatory
	        DESCRIPTION
            		"A period (in minute) AP requests update on SU Info Table from all associated SUs."
    		DEFVAL { 10 }
        	::= { su 2 }

    	suRebootAll OBJECT-TYPE
        	SYNTAX  INTEGER {
                    	deactivated(0),
                    	activated(1)
                	}
        	ACCESS  read-write
	        STATUS  mandatory
        	DESCRIPTION
            		"AP broadcasts reboot command to all subscriber units."
	        DEFVAL { deactivated }
        	::= { su 3 }

    	sudbDeleteOrAddOrModifyID OBJECT-TYPE
        	SYNTAX  INTEGER (1..126)
		ACCESS	read-write
		STATUS	mandatory
		DESCRIPTION
			"Subscriber unit ID (1..126). Each
             	 	 subscriber in a sector shall have a unique ID."
		::= { sudb 1 }

	sudbAddMAC OBJECT-TYPE
		SYNTAX	OCTET STRING (SIZE(6))
		ACCESS	read-write
		STATUS	mandatory
		DESCRIPTION
			"It is the MAC address of the subscriber unit,
		         which can be found on the back of the SU."
		::= { sudb 2 }

	sudbAddOrModifyPolling OBJECT-TYPE
		SYNTAX	INTEGER {
	        	regular(1),
                    	priority(3)
                	}
		ACCESS	read-write
		STATUS	mandatory
		DESCRIPTION
			"It is service level value, regular or priority, of a SU.
	             	 The AP will poll priority user more often, thus better
	             	 network latency as the result. As the network latency
	             	 varies based on the number of subscriber units the AP
	             	 serves, priority user is guaranteed that the latency is
        	     	 NOT greater than 100ms regardless of the size of the network."
        	DEFVAL  {regular}
		::= { sudb 3 }

	sudbAddOrModifyGroupID OBJECT-TYPE
		SYNTAX	INTEGER {
                    	nullgroup(0),
                    	group1(1),
                    	group2(2),
	              	group3(3),
        	        group4(4),
                	group5(5),
                    	group6(6),
                    	group7(7),
                    	group8(8),
                    	group9(9),
                    	groupA(10),
                    	groupB(11),
                    	groupC(12),
                    	groupD(13),
                    	groupE(14),
                    	groupF(15)
                	}
		ACCESS	read-write
		STATUS	mandatory
		DESCRIPTION
			"It is peer-to-peer group this SU belongs to.
	             	 With the SU to SU switch is turned on, SUs in
        	     	 the same peer-to-peer group can communicate to
             		 each other via the AP. There are totally 15 groups
             		 available. Note that the SU shall be set to priority
             		 user for this feature to improve latency."
        	DEFVAL  {nullgroup}
		::= { sudb 4 }

	sudbAddOrModifyDownLinkCIR OBJECT-TYPE
		SYNTAX	INTEGER (128..5000)
		ACCESS	read-write
		STATUS	mandatory
		DESCRIPTION
			"It is the DownLink Committed Information Rate (in Kbps) the AP allocates to SU."
        	DEFVAL { 256 }
		::= { sudb 5 }

	sudbAddOrModifyUpLinkCIR OBJECT-TYPE
		SYNTAX	INTEGER (128..5000)
		ACCESS	read-write
		STATUS	mandatory
		DESCRIPTION
			"It is the UpLink Committed Information Rate (in Kbps) the AP allocates to SU."
        	DEFVAL { 128 }
		::= { sudb 6 }

	sudbAddOrModifyDownLinkMIR OBJECT-TYPE
		SYNTAX	INTEGER (128..5000)
		ACCESS	read-write
		STATUS	mandatory
		DESCRIPTION
			"It is the DownLink Maximum Information Rate (in Kbps) the AP allocates to SU."
        	DEFVAL { 256 }
		::= { sudb 7 }

	sudbAddOrModifyUpLinkMIR OBJECT-TYPE
		SYNTAX	INTEGER (128..5000)
		ACCESS	read-write
		STATUS	mandatory
		DESCRIPTION
			"It is the UpLink Maximum Information Rate (in Kbps) the AP allocates to SU."
        	DEFVAL { 128 }
		::= { sudb 8 }

	sudbAdd OBJECT-TYPE
		SYNTAX	INTEGER {
                    	deactivated(0),
                    	add(1)
                	}
		ACCESS	read-write
		STATUS	mandatory
		DESCRIPTION
			"Add a subscriber (specified in object sudbDeleteOrAddID) to the subscriber database."
        	DEFVAL  {deactivated}
		::= { sudb 9 }

	sudbDelete OBJECT-TYPE
		SYNTAX	INTEGER {
                    	deactivated(0),
                    	delete(1)
                	}
		ACCESS	read-write
		STATUS	mandatory
		DESCRIPTION
			"Delete a subscriber (specified in object sudbDeleteOrAddID) from the subscriber database."
	        DEFVAL  {deactivated}
		::= { sudb 10 }

	sudbModifyPolling OBJECT-TYPE
		SYNTAX	INTEGER {
                    	deactivated(0),
                    	modify(1)
                	}
		ACCESS	read-write
		STATUS	mandatory
		DESCRIPTION
			"Modify polling attribute of a subscriber (specified in object
			 sudbDeleteOrAddOrModifyID) from the subscriber database."
	        DEFVAL  {deactivated}
		::= { sudb 11 }

	sudbModifyGroupID OBJECT-TYPE
		SYNTAX	INTEGER {
                    	deactivated(0),
                    	modify(1)
                	}
		ACCESS	read-write
		STATUS	mandatory
		DESCRIPTION
			"Modify group ID of a subscriber (specified in object
			 sudbDeleteOrAddOrModifyID) from the subscriber database."
	        DEFVAL  {deactivated}
		::= { sudb 12 }

	sudbModifyCIRMIR OBJECT-TYPE
		SYNTAX	INTEGER {
                    	deactivated(0),
                    	modify(1)
                	}
		ACCESS	read-write
		STATUS	mandatory
		DESCRIPTION
			"Modify CIR/MIR of a subscriber (specified in object
			 sudbDeleteOrAddOrModifyID) from the subscriber database."
	        DEFVAL  {deactivated}
		::= { sudb 13 }

	suResetAllSUTrafficCounters OBJECT-TYPE
		SYNTAX	INTEGER {
                        deactivated(0),
                        activated(1)
                        }
		ACCESS	read-write
		STATUS  mandatory
		DESCRIPTION
			"Clear SU traffic counters."
        	DEFVAL { deactivated }
		::= { su 5 }

	suInfoTable OBJECT-TYPE
		SYNTAX	SEQUENCE OF SuInfoEntry
		ACCESS	not-accessible
		STATUS	mandatory
		DESCRIPTION
			"A table that contains subscriber unit entities."
		::= { su 6 }

	suInfoEntry OBJECT-TYPE
		SYNTAX	SuInfoEntry
		ACCESS	not-accessible
		STATUS	mandatory
		DESCRIPTION
			"Information about a specific subscriber unit retrieved by its ID number."
		INDEX	{ suID }
		::= { suInfoTable 1 }

	SuInfoEntry ::=
		SEQUENCE {
			suID				INTEGER,
			suMAC				OCTET STRING,
			suPolling			INTEGER,
			suGroupID 			INTEGER,
			suIPAddr			IpAddress,
			suSubnetMask			IpAddress,
			suGateWay			IpAddress,
            		suRemarks               	DisplayString,
			suHWVer				DisplayString,
			suFWVer				DisplayString,
			suFWChecksum			DisplayString,
			suFPGAVer			DisplayString,
			suFPGAChecksum			DisplayString,
			suAssociation	        	INTEGER,
			suDistance			INTEGER,
			suRSSIAtSU	        	INTEGER,
			suRSSIAtAP	        	INTEGER,
			suTxPower			INTEGER,
			suEthInOctets 			Counter,
			suEthOutOctets 			Counter,
            		suRfInPackets   		Counter,
            		suRfOutPackets  		Counter,
            		suRfInDropPackets		Counter,
			suRfOutRetryAtAP		Counter,
			suRfOutRetryMaxedOutAtAP	Counter,
			suRfOutRetryAtSU		Counter,
			suRfOutRetryMaxedOutAtSU	Counter,
            		suReboot        		INTEGER,
			suBlockBroadcastMulticast	INTEGER,
			suAutoScanning 			INTEGER,
			suTcpIpServiceForAP		INTEGER,
			suHTTPD				INTEGER,
			suTCPIPForLocalEthernet		INTEGER,
			suDownLinkCIR			INTEGER,
			suUpLinkCIR			INTEGER,
			suDownLinkMIR			INTEGER,
			suUpLinkMIR			INTEGER,
			suResetTrafficCounters		INTEGER,
            		suRfInOctets 	  		Counter,
            		suRfOutOctets 	 		Counter
			}

	suID OBJECT-TYPE
		SYNTAX	INTEGER (1..126)
		ACCESS	read-only
		STATUS	mandatory
		DESCRIPTION
			"Subscriber unit ID. Each subscriber in a sector shall have a unique ID."
		::= { suInfoEntry 1 }

	suMAC OBJECT-TYPE
		SYNTAX	OCTET STRING (SIZE(6))
		ACCESS	read-only
		STATUS	mandatory
		DESCRIPTION
			"Subscriber unit MAC Address. Format: 00 01 DE xx xx xx."
		::= { suInfoEntry 2 }

	suPolling OBJECT-TYPE
		SYNTAX	INTEGER {
                    regular(1),
                    priority(3)
                }
		ACCESS	read-only
		STATUS	mandatory
		DESCRIPTION
			"It is service level value, regular or priority, of a SU.
        	         The AP will poll priority user more often, thus better
	                 network latency as the result. As the network latency
	                 varies based on the number of subscriber units the AP
	                 serves, priority user is guaranteed that the latency is
	                 NOT greater than 100ms regardless of the size of the network."
        	DEFVAL  {regular}
		::= { suInfoEntry 3 }

	suGroupID OBJECT-TYPE
		SYNTAX	INTEGER {
                    	nullgroup(0),
                    	group1(1),
                    	group2(2),
                    	group3(3),
                    	group4(4),
                    	group5(5),
                    	group6(6),
                    	group7(7),
                    	group8(8),
                    	group9(9),
                    	groupA(10),
                    	groupB(11),
                    	groupC(12),
                    	groupD(13),
                    	groupE(14),
                    	groupF(15)
                	}
		ACCESS	read-only
		STATUS	mandatory
		DESCRIPTION
			"It is peer-to-peer group this SU belongs to.
	                 With the SU to SU switch is turned on, SUs in
        	         the same peer-to-peer group can communicate to
             		 each other via the AP. There are totally 15 groups
             		 available. Note that the SU shall be set to priority
             		 user for this feature to improve latency."
	        DEFVAL  {nullgroup}
		::= { suInfoEntry 4 }

	suIPAddr OBJECT-TYPE
		SYNTAX	IpAddress
		ACCESS	read-only
		STATUS	mandatory
		DESCRIPTION
			"Subscriber unit IP Address."
		::= { suInfoEntry 5 }

	suSubnetMask OBJECT-TYPE
		SYNTAX	IpAddress
		ACCESS	read-only
		STATUS	mandatory
		DESCRIPTION
			"Subscriber unit Subnet Mask Address."
		::= { suInfoEntry 6 }

	suGateWay OBJECT-TYPE
		SYNTAX	IpAddress
		ACCESS	read-only
		STATUS	mandatory
		DESCRIPTION
			"Subscriber unit Gateway Address."
		::= { suInfoEntry 7 }

	suRemarks OBJECT-TYPE
        	SYNTAX  DisplayString (SIZE (0..30))
        	ACCESS  read-only
        	STATUS  mandatory
        	DESCRIPTION
            		"Subscriber unit Remark."
	        ::= { suInfoEntry 8 }

	suHWVer OBJECT-TYPE
		SYNTAX	DisplayString (SIZE (0..4))
		ACCESS	read-only
		STATUS	mandatory
		DESCRIPTION
			"Subscriber unit Hardware Version."
		::= { suInfoEntry 9 }

	suFWVer OBJECT-TYPE
	        SYNTAX  DisplayString (SIZE (0..32))
		ACCESS	read-only
		STATUS	mandatory
		DESCRIPTION
			"Subscriber unit main firmware version."
		::= { suInfoEntry 10 }

	suFWChecksum OBJECT-TYPE
		SYNTAX	DisplayString (SIZE (0..8))
		ACCESS	read-only
		STATUS	mandatory
		DESCRIPTION
			"Subscriber unit firmware checksum."
		::= { suInfoEntry 11 }

	suFPGAVer OBJECT-TYPE
		SYNTAX	DisplayString (SIZE (0..8))
		ACCESS	read-only
		STATUS	mandatory
		DESCRIPTION
			"Subscriber unit FPGA firmware version."
		::= { suInfoEntry 12 }

	suFPGAChecksum OBJECT-TYPE
		SYNTAX	DisplayString (SIZE (0..8))
		ACCESS	read-only
		STATUS	mandatory
		DESCRIPTION
			"Subscriber unit FPGA firmware checksum."
		::= { suInfoEntry 13 }

	suAssociation OBJECT-TYPE
	        SYNTAX  INTEGER {
        		    associating(0),
                    associated(1),
        		    authenticating(2),
                    notAssociated(3)
                }
		ACCESS	read-only
		STATUS	mandatory
		DESCRIPTION
			"Subscriber unit association status."
		::= { suInfoEntry 14 }

	suDistance OBJECT-TYPE
		SYNTAX	INTEGER (0..40)
		ACCESS	read-only
		STATUS	mandatory
		DESCRIPTION
			"Distance of SU (in 10th of a mile)."
		::= { suInfoEntry 15 }

	suRSSIAtSU OBJECT-TYPE
		SYNTAX	INTEGER (-128..127)
		ACCESS	read-only
		STATUS	mandatory
		DESCRIPTION
			"Subscriber unit RSSI at SU (in dBm)."
		::= { suInfoEntry 16 }

	suRSSIAtAP OBJECT-TYPE
		SYNTAX	INTEGER (-128..127)
		ACCESS	read-only
		STATUS	mandatory
		DESCRIPTION
			"Subscriber unit RSSI at AP (in dBm)."
		::= { suInfoEntry 17 }

	suTxPower OBJECT-TYPE
		SYNTAX	INTEGER (-128..127)
		ACCESS	read-only
		STATUS	mandatory
		DESCRIPTION
			"Subscriber unit Tx Power Level (in dBm)."
		::= { suInfoEntry 18 }

	suEthInOctets OBJECT-TYPE
		SYNTAX 	Counter
		ACCESS	read-only
		STATUS	mandatory
		DESCRIPTION
			"Number of octets received on the Ethernet port."
		::= { suInfoEntry 19 }

	suEthOutOctets OBJECT-TYPE
		SYNTAX 	Counter
		ACCESS	read-only
		STATUS	mandatory
		DESCRIPTION
			"Number of octets transmitted on the Ethernet port."
		::= { suInfoEntry 20 }

	suRfInPackets OBJECT-TYPE
		SYNTAX 	Counter
		ACCESS	read-only
		STATUS	mandatory
		DESCRIPTION
			"Number of payload packets received on the RF port."
		::= { suInfoEntry 21 }

	suRfOutPackets OBJECT-TYPE
		SYNTAX 	Counter
		ACCESS	read-only
		STATUS	mandatory
		DESCRIPTION
			"Number of payload packets transmitted on the RF port."
		::= { suInfoEntry 22 }

	suRfInDropPackets OBJECT-TYPE
		SYNTAX 	Counter
		ACCESS	read-only
		STATUS	mandatory
		DESCRIPTION
			"Number of payload drop packets received on the RF port."
		::= { suInfoEntry 23 }

	suRfOutRetryAtAP OBJECT-TYPE
		SYNTAX 	Counter
		ACCESS	read-only
		STATUS	mandatory
		DESCRIPTION
			"Number of packets AP resent to SUs through RF port."
		::= { suInfoEntry 24 }

	suRfOutRetryMaxedOutAtAP OBJECT-TYPE
		SYNTAX 	Counter
		ACCESS	read-only
		STATUS	mandatory
		DESCRIPTION
			"Number of packets AP resent to SUs through RF port hits maximum."
		::= { suInfoEntry 25 }
	suRfOutRetryAtSU OBJECT-TYPE
		SYNTAX 	Counter
		ACCESS	read-only
		STATUS	mandatory
		DESCRIPTION
			"Number of payload retry packets transmitted to the RF port."
		::= { suInfoEntry 26 }

	suRfOutRetryMaxedOutAtSU OBJECT-TYPE
		SYNTAX 	Counter
		ACCESS	read-only
		STATUS	mandatory
		DESCRIPTION
			"Number of payload retry maxed-out packets."
		::= { suInfoEntry 27 }

    	suReboot OBJECT-TYPE
        	SYNTAX  INTEGER {
                    	deactivated(0),
                    	activated(1)
                	}
	        ACCESS  read-write
        	STATUS  mandatory
	        DESCRIPTION
            		"AP issues reboot command to a specific subscriber unit."
	        DEFVAL { deactivated }
        	::= { suInfoEntry 28 }

	suBlockBroadcastMulticast OBJECT-TYPE
		SYNTAX	INTEGER {
                    disabled(0),
                    enabled(1)
                }
		ACCESS 	read-write
		STATUS 	mandatory
		DESCRIPTION
			"When it is turned on, then the SU will block all the broadcast/multicast packets."
		::= { suInfoEntry 29 }

	suAutoScanning OBJECT-TYPE
		SYNTAX	INTEGER {
                    disabled(0),
                    enabled(1)
                }
		ACCESS 	read-write
		STATUS 	mandatory
		DESCRIPTION
			"When it is turned on, then the SU will scan all channels during boot-up."
		::= { suInfoEntry 30 }

	suTcpIpServiceForAP OBJECT-TYPE
		SYNTAX	INTEGER {
                    disabled(0),
                    enabled(1)
                }
		ACCESS 	read-write
		STATUS 	mandatory
		DESCRIPTION
			"When it is turned on, then the SU will serve the TCP/IP service for AP."
		::= { suInfoEntry 31 }

	suHTTPD OBJECT-TYPE
		SYNTAX	INTEGER {
                    disabled(0),
                    enabled(1)
                }
		ACCESS 	read-write
		STATUS 	mandatory
		DESCRIPTION
			"When it is turned on, then the SU will serve the web service."
		::= { suInfoEntry 32 }

	suTCPIPForLocalEthernet OBJECT-TYPE
		SYNTAX	INTEGER {
                    disabled(0),
                    enabled(1)
                }
		ACCESS 	read-write
		STATUS 	mandatory
		DESCRIPTION
			"When it is turned on, then the SU will process all the local TCP/IP service."
		::= { suInfoEntry 33 }

	suDownLinkCIR OBJECT-TYPE
		SYNTAX	INTEGER (128..5000)
		ACCESS	read-only
		STATUS	mandatory
		DESCRIPTION
			"It is the DownLink Committed Information Rate (in Kbps) the AP allocates to SU."
		::= { suInfoEntry 34 }

	suUpLinkCIR OBJECT-TYPE
		SYNTAX	INTEGER (128..5000)
		ACCESS	read-only
		STATUS	mandatory
		DESCRIPTION
			"It is the UpLink Committed Information Rate (in Kbps) the AP allocates to SU."
		::= { suInfoEntry 35 }

	suDownLinkMIR OBJECT-TYPE
		SYNTAX	INTEGER (128..5000)
		ACCESS	read-only
		STATUS	mandatory
		DESCRIPTION
			"It is the DownLink Maximum Information Rate (in Kbps) the AP allocates to SU."
		::= { suInfoEntry 36 }

	suUpLinkMIR OBJECT-TYPE
		SYNTAX	INTEGER (128..5000)
		ACCESS	read-only
		STATUS	mandatory
		DESCRIPTION
			"It is the UpLink Maximum Information Rate (in Kbps) the AP 			allocates to SU."
		::= { suInfoEntry 37 }

	suResetTrafficCounters OBJECT-TYPE
		SYNTAX	INTEGER {
                        deactivated(0),
                        activated(1)
                        }
		ACCESS	read-write
		STATUS  mandatory
		DESCRIPTION
			"Clear the traffic counters."
        	DEFVAL { deactivated }
		::= { suInfoEntry 38 }

	suRfInOctets OBJECT-TYPE
		SYNTAX 	Counter
		ACCESS	read-only
		STATUS	mandatory
		DESCRIPTION
			"Number of payload octets received on the RF port."
		::= { suInfoEntry 39 }

	suRfOutOctets OBJECT-TYPE
		SYNTAX 	Counter
		ACCESS	read-only
		STATUS	mandatory
		DESCRIPTION
			"Number of payload octets transmitted on the RF port."
		::= { suInfoEntry 40 }

	-- trapconfig objects
	trapconfigTrapCount OBJECT-TYPE
		SYNTAX	INTEGER (0..255)
		ACCESS	read-only
		STATUS	mandatory
		DESCRIPTION
			"Types of trap."
		::= { trapconfig 1 }
        
    	trapconfigDest1IPAddress OBJECT-TYPE
		SYNTAX	IpAddress
		ACCESS	read-write
		STATUS	mandatory
		DESCRIPTION
			"Trap destination 1 IP address."
		::= { trapconfig 2 }
         
    	trapconfigDest2IPAddress OBJECT-TYPE
		SYNTAX	IpAddress
		ACCESS	read-write
		STATUS	mandatory
		DESCRIPTION
			"Trap destination 2 IP address."
		::= { trapconfig 3 }
 
	trapconfigTrapTable OBJECT-TYPE
		SYNTAX	SEQUENCE OF TrapconfigTrapEntry
		ACCESS	not-accessible
		STATUS	mandatory
		DESCRIPTION
			"A table that contains information of Trango trap events ."
		::= { trapconfig 4 }
	
	trapconfigTrapEntry OBJECT-TYPE
		SYNTAX	TrapconfigTrapEntry
		ACCESS	not-accessible
		STATUS	mandatory
		DESCRIPTION
			"Information about a specific Trango trap event."
		INDEX	{ aptrpIndex }
		::= { trapconfigTrapTable 1 }

	TrapconfigTrapEntry ::=
		SEQUENCE {
			aptrpIndex
				INTEGER,
			aptrpID
				INTEGER,
			aptrpCommStr
				DisplayString,
			aptrpEnable
				INTEGER
		}

	aptrpIndex	OBJECT-TYPE
		SYNTAX	INTEGER (1..5)
		ACCESS	read-only
		STATUS	mandatory
		DESCRIPTION
			"Trap index."
		::= { trapconfigTrapEntry 1 }
	
	aptrpID	OBJECT-TYPE
		SYNTAX	INTEGER (7..255)
		ACCESS	read-only
		STATUS	mandatory
		DESCRIPTION
			"Specific trap ID."
		::= { trapconfigTrapEntry 2 }
	
	aptrpCommStr OBJECT-TYPE
        SYNTAX  DisplayString (SIZE (0..32))
		ACCESS	read-write
		STATUS	mandatory
		DESCRIPTION
			"Specific trap community string."
		::= { trapconfigTrapEntry 3 }
	
    	aptrpEnable OBJECT-TYPE
		SYNTAX	INTEGER {
                    disabled(0),
                    enabled(1)
                }
		ACCESS	read-write
		STATUS	mandatory
		DESCRIPTION
			"Enable a specific Trango trap event or not."
	        DEFVAL  {disabled}
		::= { trapconfigTrapEntry 4 }
	
	-- MIB version object
	mibinfoVersion OBJECT-TYPE
        SYNTAX  DisplayString (SIZE (0..32))
		ACCESS	read-only
		STATUS	mandatory
		DESCRIPTION
			"Trango MIB Version."
		::= { mibinfo 1 }

	-- Trap objects
	suLinkUp TRAP-TYPE
		ENTERPRISE m2400straps
		VARIABLES { suID }
		DESCRIPTION
		  	"The SNMP trap that is generated when a specific SU Associated."
		::= 7

	suLinkDown TRAP-TYPE
		ENTERPRISE m2400straps
		VARIABLES { suID }
		DESCRIPTION
		  	"The SNMP trap that is generated when a specific SU Powered Off."
		::= 8

-- End of file <trango_M2400SAP_1p0.mib>
END
