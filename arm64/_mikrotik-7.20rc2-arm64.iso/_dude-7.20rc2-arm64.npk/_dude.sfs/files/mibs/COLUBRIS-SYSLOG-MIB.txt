-- *****************************************************************
-- COLUBRIS-SYSLOG-MIB.my:  Colubris Networks Syslog MIB file
--
-- November 2001
--
-- Copyright (c) 2001, 2002  by Colubris Networks, Inc.
-- All rights reserved.
-- *****************************************************************

COLUBRIS-SYSLOG-MIB DEFINITIONS ::= BEGIN

IMPORTS
	MODULE-IDENTITY,
	OBJECT-TYPE,
	NOTIFICATION-TYPE
		FROM SNMPv2-SMI
	TEXTUAL-CONVENTION, 
	TimeStamp,
	DisplayString
		FROM SNMPv2-TC
	MODULE-COMPLIANCE,
	OBJECT-GROUP
		FROM SNMPv2-CONF
	colubrisMgmt
		FROM COLUBRIS-SMI;

colubrisSyslogMIB  MODULE-IDENTITY
	LAST-UPDATED "200111210000Z"
	ORGANIZATION "Colubris Networks, Inc."
	CONTACT-INFO
		"	Colubris Networks
			Customer Service

		Postal: 420 Armand-Frappier, Suite 200
			Laval, QC  H7V 4B4
			CANADA

		   Tel: +1 450 680-1661

		E-mail: cn-snmp@colubris.com"
	DESCRIPTION
		"Initial version of the SYSLOG MIB module."
	::= { colubrisMgmt 3 }

-- colubrisSyslogMIB definition

colubrisSyslogMIBObjects OBJECT IDENTIFIER ::= { colubrisSyslogMIB 1 }

-- MIB defines the following groupings

syslogConfig OBJECT IDENTIFIER ::=	{ colubrisSyslogMIBObjects 1 }
syslogMessage OBJECT IDENTIFIER ::= { colubrisSyslogMIBObjects 2 }

SyslogSeverity ::= TEXTUAL-CONVENTION
	STATUS	current
	DESCRIPTION
		"Indicates the severity of a syslog message. This values is the
		actual value the syslog daemon uses, plus 1. For example: the
		value for debug severity will be 8 instead of 7."
	SYNTAX	INTEGER
	{
		emergency(1),
		alert(2),
		critical(3),
		error(4),
		warning(5),
		notice(6),
		info(7),
		debug(8)
	}

syslogSeverityNotificationEnabled OBJECT-TYPE 
	SYNTAX	INTEGER
	{
		disabled(0),
		enabled(1)
	}
	MAX-ACCESS	read-write
	STATUS	current
	DESCRIPTION
		"Specifies if syslogSeverityNotification notifications will be sent."
	DEFVAL	{ disabled }
	::= { syslogConfig 1 }

syslogRegExMatchNotificationEnabled OBJECT-TYPE 
	SYNTAX	INTEGER
	{
		disabled(0),
		enabled(1)
	}
	MAX-ACCESS	read-write
	STATUS	current
	DESCRIPTION
		"Specifies if syslogRegExMatchNotification notifications will be sent."
	DEFVAL	{ disabled }
	::= { syslogConfig 2 }	

syslogSeverityLevel OBJECT-TYPE
	SYNTAX	SyslogSeverity
	MAX-ACCESS	read-write
	STATUS	current
	DESCRIPTION
		"Specifies the severity level of messages that the syslog daemon will 
		 log. Only messages with a severity level equal to or greater than 
		 syslogSeverityLevel will be logged. A value of error(4) means that 
		 messages with warning, notice, info or debug severity will not be logged."
	DEFVAL	{ warning }
	::= { syslogConfig 3 }
	
syslogTrapSeverityLevel OBJECT-TYPE
	SYNTAX	SyslogSeverity
	MAX-ACCESS	read-write
	STATUS	current
	DESCRIPTION
		"Specifies the severity level of messages that will generate a 
		 syslogSeverityNotification notification. A value of error(4) means 
		 that messages with warning, notice, info or debug severity will 
		 never generate a notification." 
	DEFVAL	{ warning }
	::= { syslogConfig 4 }

syslogMessageRegEx OBJECT-TYPE
	SYNTAX	DisplayString
	MAX-ACCESS	read-write
	STATUS	current
	DESCRIPTION
		"Specifies the regular expression that will trigger a syslogRegExMatchNotification.
		 When set to an empty string, there is no attempt to match the syslog
	 	 message generated by the device with the content of syslogMessageRegEx."
	::= { syslogConfig 5 }    

syslogMsgNumber OBJECT-TYPE
	SYNTAX	INTEGER
	MAX-ACCESS  not-accessible	
	STATUS	current
	DESCRIPTION
		"A unique ID representing a message."
	::= { syslogMessage 1 }
	
syslogMsgFacility OBJECT-TYPE
	SYNTAX	DisplayString	
	MAX-ACCESS	not-accessible
	STATUS	current
	DESCRIPTION
		"A string representing the facility that sent the message."
	::= { syslogMessage 2  }

syslogMsgSeverity OBJECT-TYPE
	SYNTAX	SyslogSeverity
	MAX-ACCESS	not-accessible
	STATUS	current
	DESCRIPTION
		"The severity level of the message."
	::= { syslogMessage 3  }

syslogMsgText OBJECT-TYPE
	SYNTAX	DisplayString	
	MAX-ACCESS	not-accessible
	STATUS	current
	DESCRIPTION
		"The message."
	::= { syslogMessage 4 }

-- notifications

colubrisSyslogMIBNotificationPrefix OBJECT IDENTIFIER ::= { colubrisSyslogMIB 2 }
colubrisSyslogMIBNotifications OBJECT IDENTIFIER ::= {colubrisSyslogMIBNotificationPrefix 0  }

syslogSeverityNotification NOTIFICATION-TYPE
	OBJECTS
	{
		syslogMsgNumber,
		syslogMsgFacility,
		syslogMsgSeverity,
		syslogMsgText
	}
	STATUS	current
	DESCRIPTION
		"Sent when the device generated a syslog message that is 
		 of the right severity level. This severity level is set by
		 syslogTrapSeverityLevel."
  --#SUMMARY "Syslog severity trap for msg #%d severity %d: %s - %s"
  --#ARGUMENTS { 0, 2, 1, 3 }
  --#SEVERITY MAJOR
  --#CATEGORY "Colubris Networks Alarms"
	::= { colubrisSyslogMIBNotifications 1 }

syslogRegExMatchNotification NOTIFICATION-TYPE
	OBJECTS
	{
		syslogMsgNumber,
		syslogMsgFacility,
		syslogMsgSeverity,
		syslogMsgText
	}
	STATUS	current
	DESCRIPTION
		"Sent when the device generated a syslog message that 
		 matches the regular expression specified in syslogMessageRegEx."
  --#SUMMARY "Syslog regex match trap for msg #%d severity %d: %s - %s"
  --#ARGUMENTS { 0, 2, 1, 3 }
  --#SEVERITY MAJOR
  --#CATEGORY "Colubris Networks Alarms"
	::= { colubrisSyslogMIBNotifications 2 }
	
-- conformance information

colubrisSyslogMIBConformance OBJECT IDENTIFIER ::= { colubrisSyslogMIB 3 }
colubrisSyslogMIBCompliances OBJECT IDENTIFIER ::= { colubrisSyslogMIBConformance 1 }
colubrisSyslogMIBGroups      OBJECT IDENTIFIER ::= { colubrisSyslogMIBConformance 2 }

-- compliance statements     

colubrisSyslogMIBCompliance MODULE-COMPLIANCE
	STATUS current
	DESCRIPTION
		"The compliance statement for entities which implement
		 the Colubris Networks Syslog MIB."
	MODULE
		MANDATORY-GROUPS { colubrisSyslogMIBGroup }
	::= { colubrisSyslogMIBCompliances 1 }
	
-- units of conformance

colubrisSyslogMIBGroup OBJECT-GROUP
	OBJECTS
	{
		syslogSeverityNotificationEnabled,
		syslogRegExMatchNotificationEnabled,
		syslogSeverityLevel,
		syslogTrapSeverityLevel,		
		syslogMessageRegEx
	}
	STATUS current
	DESCRIPTION
		"A collection of objects providing the Syslog MIB capability."
	::= { colubrisSyslogMIBGroups 1 }
END
