-- Title:      ATMEL  Private MIB                                          

ATMEL-MIB DEFINITIONS ::= BEGIN

--IMPORTS
--	enterprises,Counter
--FROM RFC1155-SMI
--	DisplayString
--FROM RFC1213-MIB;
--	TRAP-TYPE
--FROM RFC-1215;


--MacAddress ::= IMPLICIT OCTET STRING (SIZE(6))
DisplayString ::= OCTET STRING

internet      OBJECT IDENTIFIER ::= { iso org(3) dod(6) 1 }
directory     OBJECT IDENTIFIER ::= { internet 1 }
mgmt          OBJECT IDENTIFIER ::= { internet 2 }
experimental  OBJECT IDENTIFIER ::= { internet 3 }
private       OBJECT IDENTIFIER ::= { internet 4 }
enterprises   OBJECT IDENTIFIER ::= { private 1 }

atmel       OBJECT IDENTIFIER ::= { enterprises 410 }
atmelmib    OBJECT IDENTIFIER ::= { atmel 1}
atmelSys	OBJECT IDENTIFIER ::= {atmelmib 1}
wireless	OBJECT IDENTIFIER ::= {atmelmib 2}
traps 	OBJECT IDENTIFIER ::= {atmelmib 3 }



--*************************** System***************************
--****************************************************************



sysCtrlGRP OBJECT IDENTIFIER ::= {atmelSys 1}

sysDescr OBJECT-TYPE
    SYNTAX  DisplayString (SIZE (0..255))
    ACCESS  read-only
    STATUS  mandatory
       DESCRIPTION
         "A textual description of the entity.  This value
          should include the full name and version
          identification of the system's hardware type,
          software operating-system, and networking
          software.  It is mandatory that this only contain
          printable ASCII characters."
	::= { sysCtrlGRP 1 } 


sysReset OBJECT-TYPE
	SYNTAX INTEGER {enable(1),disable(2)}
	ACCESS  read-write
	STATUS  mandatory
	DESCRIPTION       
	"By setting this attribute enable(1), a reset command to 
	the system is issued." 
	::= { sysCtrlGRP 2 } 

sysTrapSwitch OBJECT-TYPE
	SYNTAX INTEGER {enable(1),disable(2)}
	ACCESS read-write
	STATUS mandatory
	DESCRIPTION
	"This attribute enables the transmission of SNMP.V1 TRAPs."
	::= {sysCtrlGRP 3}

sysLoadDefaults OBJECT-TYPE
	SYNTAX INTEGER { enable(1), disable(2) }
	ACCESS  read-write
	STATUS  mandatory
	DESCRIPTION       
	"Setting this attribute to enable(1), will cause the system to load
	the factory default values of all the operational parameters." 
	::= { sysCtrlGRP 4 }

sysDeviceInfo 	OBJECT-TYPE
			SYNTAX OCTET STRING (SIZE (92))
			ACCESS read-only
			STATUS mandatory
			DESCRIPTION	 
			"Hardware device configuration struct."
			::= {sysCtrlGRP 5 }

sysUpload OBJECT-TYPE
	SYNTAX INTEGER {enable(1),disable(2)}
	ACCESS  read-write
	STATUS  mandatory
	DESCRIPTION       
	"By setting this attribute enable(1), a Upload configuration command to 
	the system is issued." 
	::= { sysCtrlGRP 6 } 



-----------------------------BridgingLevel-----------------------------

operBridgingLevel OBJECT IDENTIFIER ::= {atmelSys 2}

operIPAddress OBJECT-TYPE
		SYNTAX IpAddress
		ACCESS read-write
		STATUS mandatory
		DESCRIPTION	 
		"The IP address of this device used over its Ethernet
		or Wireless LAN port."
		::= { operBridgingLevel 1 }

operIPMask OBJECT-TYPE
	    SYNTAX  IpAddress
	    ACCESS  read-write
	    STATUS  mandatory
	    DESCRIPTION
	    "The IP Network mask used by the IP entity when accessing
	    devices through any of its LAN Ports (Ethernet or WLAN)."
	    ::= { operBridgingLevel 2}

operEthernetAddress OBJECT-TYPE
	    SYNTAX  OCTET STRING (SIZE (6))
	    ACCESS  read-write
	    STATUS  mandatory
	    DESCRIPTION
	    "The MAC Address of the Ethernet interface."
	    ::= { operBridgingLevel 3}


operGateway OBJECT-TYPE
		SYNTAX IpAddress
		ACCESS read-write
		STATUS mandatory
		DESCRIPTION	 
		"."
		::= { operBridgingLevel 4 }

operDHCP OBJECT-TYPE
		SYNTAX	INTEGER {enable(1),disable(2)}
		ACCESS read-write
		STATUS mandatory
		DESCRIPTION	 
		"When setting this attribute to ENABLE, the system will
		enable DHCP protocol."
		::= { operBridgingLevel 5 }

operPrimaryPort OBJECT-TYPE
		SYNTAX	INTEGER {Ethernet(1),Wireless(2)}
		ACCESS read-write
		STATUS mandatory
		DESCRIPTION	 
		"This attribute indicates the primaty port."
		::= { operBridgingLevel 6 }



-----------------------------Filtering-----------------------------



operFiltering OBJECT IDENTIFIER ::= {atmelSys 3}

operIPFilter OBJECT-TYPE
		SYNTAX	INTEGER {enable(1), disable(2)}
		ACCESS read-write
		STATUS mandatory
		DESCRIPTION	 
		"When setting this attribute to ENABLE, the system will
		filter out all non IP-traffic."
		::= { operFiltering 1 }



-----------------------------Bridge Operational Mode -----------------------------


operBridgeOperationalMode OBJECT IDENTIFIER ::= {atmelSys 4}


bridgeOperationalMode OBJECT-TYPE
		SYNTAX	INTEGER {WBPoint2Multipoint(1), AP(2), APclient(3),  WBPoint2Point(3)}
		ACCESS read-write
		STATUS mandatory
		DESCRIPTION	 
		"The Operational Mode of Bridge. Access Point, Access Point client, Wireless Bridge Point to Point, Wireless Bridge Point to MultiPoint."
		::= { operBridgeOperationalMode 1 }

bridgeRemoteBridgeBSSID OBJECT-TYPE
		SYNTAX	OCTET STRING (SIZE (6))
		ACCESS read-write
		STATUS mandatory
		DESCRIPTION	 
		"The Preferred BSSID if the device is at Access Point client mode
		or the remote Mac if the device is at Wireless Bridge Point to Point mode."
		::= { operBridgeOperationalMode 2 }



-----------------------------Static-----------------------------


dot1dStatic OBJECT IDENTIFIER ::= {atmelSys 5}


StaticMacFilterNum OBJECT-TYPE
      SYNTAX  INTEGER 
      ACCESS  read-write
      STATUS  mandatory
      DESCRIPTION
      "This parameter's value indicates the number of the currently
      static MAC filters."
      ::= { dot1dStatic 1 }


          dot1dStaticTable OBJECT-TYPE
              SYNTAX  SEQUENCE OF Dot1dStaticEntry
              ACCESS  not-accessible
              STATUS  mandatory
              DESCRIPTION
                      "A table containing filtering information
                      configured into the bridge by (local or network)
                      management specifying the set of ports to which
                      frames received from specific ports and containing
                      specific destination addresses are allowed to be
                      forwarded.  The value of zero in this table as the
                      port number from which frames with a specific
                      destination address are received, is used to
                      specify all ports for which there is no specific
                      entry in this table for that particular
                      destination address.  Entries are valid for
                      unicast and for group/broadcast addresses."
              REFERENCE
                      "IEEE 802.1D-1990: Section 6.7.2"
              ::= { dot1dStatic 2 }

          dot1dStaticEntry OBJECT-TYPE
              SYNTAX  Dot1dStaticEntry
              ACCESS  not-accessible
              STATUS  mandatory
              DESCRIPTION
                      "Filtering information configured into the bridge
                      by (local or network) management specifying the
                      set of ports to which frames received from a
                      specific port and containing a specific
                      destination address are allowed to be forwarded."
              REFERENCE
                      "IEEE 802.1D-1990: Section 6.7.2"
              INDEX   { dot1dStaticAddress}--, dot1dStaticReceivePort }
              ::= { dot1dStaticTable 1 }

          Dot1dStaticEntry ::=
              SEQUENCE {
                  dot1dStaticAddress
                      OCTET STRING (SIZE (6))
--                  dot1dStaticReceivePort
--                     INTEGER,
--                  dot1dStaticAllowedToGoTo
--                      INTEGER,
--                  dot1dStaticStatus
--                      INTEGER
              }

          dot1dStaticAddress OBJECT-TYPE
              SYNTAX  OCTET STRING (SIZE (6))
              ACCESS  read-write
              STATUS  mandatory
              DESCRIPTION
                      "The destination MAC address in a frame to which
                      this entry's filtering information applies.  This
                      object can take the value of a unicast address, a
                      group address or the broadcast address."
              REFERENCE
                      "IEEE 802.1D-1990: Section 3.9.1, 3.9.2"
              ::= { dot1dStaticEntry 1 }

--          dot1dStaticReceivePort OBJECT-TYPE
--              SYNTAX  INTEGER
--              ACCESS  read-write
--              STATUS  mandatory
--              DESCRIPTION
--                      "Either the value '0', or the port number of the
--                      port from which a frame must be received in order
--                      for this entry's filtering information to apply.
--                      A value of zero indicates that this entry applies
--                      on all ports of the bridge for which there is no
--                      other applicable entry."
--              ::= { dot1dStaticEntry 2 }

--          dot1dStaticAllowedToGoTo OBJECT-TYPE
--              SYNTAX  INTEGER
--              ACCESS  read-write
--              STATUS  mandatory
--              DESCRIPTION
--                      "The set of ports to which frames received from a
--                      specific port and destined for a specific MAC
--                      address, are allowed to be forwarded.  Each octet
--                      within the value of this object specifies a set of
--                      eight ports, with the first octet specifying ports
--                      1 through 8, the second octet specifying ports 9
--                      through 16, etc.  Within each octet, the most
--                      significant bit represents the lowest numbered
--                      port, and the least significant bit represents the
--                      highest numbered port.  Thus, each port of the
--                      bridge is represented by a single bit within the
--                      value of this object.  If that bit has a value of
--                      '1' then that port is included in the set of
--                      ports; the port is not included if its bit has a
--                      value of '0'.  (Note that the setting of the bit
--                      corresponding to the port from which a frame is
--                      received is irrelevant.)  The default value of
--                      this object is a string of ones of appropriate
--                      length."
--              ::= { dot1dStaticEntry 3 }
--
--          dot1dStaticStatus OBJECT-TYPE
--              SYNTAX  INTEGER {
--                          other(1),
--                          invalid(2),
--                          permanent(3),
--                          deleteOnReset(4),
--                          deleteOnTimeout(5)
--                      }
--              ACCESS  read-write
--              STATUS  mandatory
--              DESCRIPTION
--                      "This object indicates the status of this entry.
--                      The default value is permanent(3).
--                           other(1) - this entry is currently in use but
--                                the conditions under which it will
--                                remain so are different from each of the
--                                following values.
--                           invalid(2) - writing this value to the object
--                                removes the corresponding entry.
--                           permanent(3) - this entry is currently in use
--                                and will remain so after the next reset
--                                of the bridge.
--                           deleteOnReset(4) - this entry is currently in
--                                use and will remain so until the next
--                                reset of the bridge.
--                           deleteOnTimeout(5) - this entry is currently
--                                in use and will remain so until it is
--                                aged out."
--              ::= { dot1dStaticEntry 4 }



----------------------------------Protocol Filtering-------------------


ProtocolFilterGRP OBJECT IDENTIFIER ::= {atmelSys 6}

ProtocolFilterNum OBJECT-TYPE
      SYNTAX  INTEGER 
      ACCESS  read-write
      STATUS  mandatory
      DESCRIPTION
      "This parameter's value indicates the number of the currently
      protocol filters."
      ::= { ProtocolFilterGRP 1 }




          ProtocolFilterTable OBJECT-TYPE
              SYNTAX  SEQUENCE OF ProtocolFilterEntry
              ACCESS  not-accessible
              STATUS  mandatory
              DESCRIPTION
                      "A table containing filtering information
                      configured into the bridge by (local or network)
                      management specifying the set of protocol filter."
              ::= { ProtocolFilterGRP 2 }

          protocolFilterEntry OBJECT-TYPE
              SYNTAX  ProtocolFilterEntry
              ACCESS  not-accessible
              STATUS  mandatory
              DESCRIPTION
                      "Filtering information configured into the bridge
                      by (local or network) management specifying the
                      set of protocol filter."
              INDEX   { ProtocolFilterCode }
              ::= { ProtocolFilterTable 1 }

          ProtocolFilterEntry ::=
              SEQUENCE {
                  ProtocolFilterCode
                      OCTET STRING (SIZE (2)),
                  ProtocolFilterDescription
                      DisplayString (SIZE (0..255)),
                  ProtocolFilterActivity
                      INTEGER
              }

          ProtocolFilterCode OBJECT-TYPE
              SYNTAX  OCTET STRING (SIZE (2))
              ACCESS  read-write
              STATUS  mandatory
              DESCRIPTION
                      "The protocol code configured into the bridge
                      by (local or network) management specifying the
                      set of protocol filter."
              ::= { protocolFilterEntry 1 }

          ProtocolFilterDescription OBJECT-TYPE
              SYNTAX  DisplayString (SIZE (0..255))
              ACCESS  read-write
              STATUS  mandatory
              DESCRIPTION
                      "A textual description of the protocol."
              ::= { protocolFilterEntry 2 }

          ProtocolFilterActivity OBJECT-TYPE
              SYNTAX  INTEGER {enable(1),disable(2)}
              ACCESS  read-write
              STATUS  mandatory
              DESCRIPTION
                      "This object indicates the status of this filter."
              ::= { protocolFilterEntry 3 }



-----------------------------Ethernet STATISTICS-----------------------------


EthStatisticsGRP OBJECT IDENTIFIER ::= {atmelSys 7}

EthRxStatistics OBJECT-TYPE
		SYNTAX OCTET STRING (SIZE (64))
		ACCESS read-only
		STATUS mandatory
		DESCRIPTION	 
		"Ethernet Rx Statistics."
		::= {EthStatisticsGRP 1 }

EthTxStatistics OBJECT-TYPE
		SYNTAX OCTET STRING (SIZE (56))
		ACCESS read-only
		STATUS mandatory
		DESCRIPTION	 
		"Ethernet Tx Statistics."
		::= {EthStatisticsGRP 2 }





-----------------------------Test Mode Settings-----------------------------


TestModeSettingsGRP OBJECT IDENTIFIER ::= {atmelSys 8}

TestModeOnOff 	OBJECT-TYPE
				SYNTAX INTEGER {enable(1),disable(2)}
				ACCESS read-write
				STATUS mandatory
				DESCRIPTION	 
				"."
				::= { TestModeSettingsGRP 1 }


TestModeCommandStruct 	OBJECT-TYPE
				SYNTAX OCTET STRING (SIZE (8))
				ACCESS read-write
				STATUS mandatory
				DESCRIPTION	 
				"."
				::= {TestModeSettingsGRP 2 }

TestModeRadioConfiguration 	OBJECT-TYPE
					SYNTAX OCTET STRING (SIZE (14))
					ACCESS read-write
					STATUS mandatory
					DESCRIPTION	 
					"Configuration of radio derive from tests."
					::= {TestModeSettingsGRP 8 }

TestModeStatistics	 	OBJECT-TYPE
					SYNTAX OCTET STRING (SIZE (8))
					ACCESS read-only
					STATUS mandatory
					DESCRIPTION	 
					"Statistics derive from tests."
					::= {TestModeSettingsGRP 9 }




-----------------------------Authorized Settings-----------------------------


AuthorizedSettingsGRP OBJECT IDENTIFIER ::= {atmelSys 9}

AuthorizedUserPass 	OBJECT-TYPE
				SYNTAX OCTET STRING (SIZE (16))
				ACCESS read-write
				STATUS mandatory
				DESCRIPTION	 
				"."
				::= {AuthorizedSettingsGRP 1 }


AuthorizedAdminPass 	OBJECT-TYPE
				SYNTAX OCTET STRING (SIZE (16))
				ACCESS read-write
				STATUS mandatory
				DESCRIPTION	 
				"."
				::= {AuthorizedSettingsGRP 2 }


AuthorizedManufactPass 	OBJECT-TYPE
				SYNTAX OCTET STRING (SIZE (16))
				ACCESS read-write
				STATUS mandatory
				DESCRIPTION	 
				"."
				::= {AuthorizedSettingsGRP 3 }


--*************************** wireless ***************************
--****************************************************************

-----------------------------Operational Settings-----------------------------


OperationalSettingsGRP OBJECT IDENTIFIER ::= {wireless 1}




operChannelID  OBJECT-TYPE
	SYNTAX  INTEGER  {
			channel1(1),
			channel2(2),
			channel3(3),
			channel4(4),
			channel5(5),
			channel6(6),
			channel7(7),
			channel8(8),
			channel9(9),
			channel10(10),
			channel11(11),
			channel12(12),
			channel13(13),
			channel14(14)
		}
	ACCESS  read-write
	STATUS  mandatory
	DESCRIPTION
		"The operating frequency channel. Valid numbers
		are	as defind in ISO/IEC 8802-11:1999, 15.4.6.2."
	::= { OperationalSettingsGRP 1 }


operESSIDLength OBJECT-TYPE
     SYNTAX  INTEGER
     ACCESS  read-write    
     STATUS  mandatory
     DESCRIPTION
     "The ESSID Length"
     ::= {OperationalSettingsGRP 2 }     

operESSID OBJECT-TYPE
     SYNTAX  OCTET STRING (SIZE (32))
     ACCESS  read-write    
     STATUS  mandatory
     DESCRIPTION
     "The network name. The size of the network name
     should not be more than 32 characters long."
     ::= {OperationalSettingsGRP 3 }     


operRTSThreshold OBJECT-TYPE
		SYNTAX	INTEGER  
		ACCESS read-write
		STATUS mandatory
		DESCRIPTION	 
		"This attribute indicates the number of bytes in an 
		MPDU (frame), above which an RTS/CTS handshake will be
		performed. Setting this attribute to be larger than the
		maximum frame size, will prevent the RTS/CTS handshake 
		for frames trassmitted by this station."
	::= {OperationalSettingsGRP 4 }


operFragmentationThreshold OBJECT-TYPE
		SYNTAX	INTEGER  
		ACCESS read-write
		STATUS mandatory
		DESCRIPTION	 
		"This attribute indicates the number of bytes in an 
		MPDU (frame), above which MPDU fragmentation will be
		performed."
	::= {OperationalSettingsGRP 5 }
	

operPreambleType OBJECT-TYPE
      SYNTAX  INTEGER {
			ShortPreamble(1),
			LongPreamble(2)
		}
      ACCESS  read-write
      STATUS  mandatory
      DESCRIPTION
      "This parameter's value indicates the number of the currently
      associated STAtions. Associated STAtions should not be more
      than 2007."
	      ::= {OperationalSettingsGRP 6 }


operAuthenticationType OBJECT-TYPE
		SYNTAX	INTEGER {
      	openSystem(1),
      	sharedKey(2),
      	BothType(3)
      	}
		ACCESS read-write
		STATUS mandatory
		DESCRIPTION	 
		"This attribute indicates the authentication algorithm
		used during the authentication sequence.
		The value of this attribute is one of the following:
		1 - Open System,
		2 - Shared Key
		3 - Both Type "
		::= {OperationalSettingsGRP 7 }


operBasicRates OBJECT-TYPE
		SYNTAX OCTET STRING (SIZE (4))
		ACCESS read-write
		STATUS mandatory
		DESCRIPTION	 
		"This attribute indicates the basic rates of AP-Bridge."
		::= { OperationalSettingsGRP 8 }


operAutoRateFallBack OBJECT-TYPE
		SYNTAX INTEGER {enable(1),disable(2)}
		ACCESS read-write
		STATUS mandatory
		DESCRIPTION	 
		"This attribute indicates if Auto Rate Fall Back is enable or disable."
		::= {OperationalSettingsGRP 9 }

operAccessPointName OBJECT-TYPE
     SYNTAX  OCTET STRING (SIZE (32))
     ACCESS  read-write    
     STATUS  mandatory
     DESCRIPTION
     "The AP name."
     ::= {OperationalSettingsGRP 10 }     



-----------------------------Privacy-----------------------------


privacyGRP OBJECT IDENTIFIER ::= { wireless 2 }



defaultWEPKey1 OBJECT-TYPE
    SYNTAX OCTET STRING (SIZE (13))
    ACCESS  read-write
    STATUS  mandatory
    DESCRIPTION    
    "A WEP default secret key value."
    ::= { privacyGRP 1 }    

defaultWEPKey2 OBJECT-TYPE
    SYNTAX OCTET STRING (SIZE (13))
    ACCESS  read-write
    STATUS  mandatory
    DESCRIPTION    
    "A WEP default secret key value."
    ::= { privacyGRP 2 }    

defaultWEPKey3 OBJECT-TYPE
    SYNTAX OCTET STRING (SIZE (13))
    ACCESS  read-write
    STATUS  mandatory
    DESCRIPTION    
    "A WEP default secret key value."
    ::= { privacyGRP 3 }    

defaultWEPKey4 OBJECT-TYPE
    SYNTAX OCTET STRING (SIZE (13))
    ACCESS  read-write
    STATUS  mandatory
    DESCRIPTION    
    "A WEP default secret key value."
    ::= { privacyGRP 4 }    



privacyWEPEnable OBJECT-TYPE
		SYNTAX INTEGER {enable64(1),disable(2),enable128(3) }
		ACCESS read-write
		STATUS mandatory
		DESCRIPTION	 
		"This attribute, when true, indicates that the 802.11
		standard encryption mechanism (WEP) is implemented."
		::= {privacyGRP 5}


privacyDefaultWEPKeyID OBJECT-TYPE
		SYNTAX INTEGER   (1..4)
		ACCESS read-write
		STATUS mandatory
		DESCRIPTION
		"This attribute shall indicate the use of the first, second,
		third or fourth DefaultWEPKey when set to values of one, two,
		three or four."
		::= {privacyGRP 6}


-----------------------------STATISTICS-----------------------------


WLstatisticsGRP OBJECT IDENTIFIER ::= {wireless 3}

wirelessStatistics OBJECT-TYPE
		SYNTAX OCTET STRING (SIZE (88))
		ACCESS read-only
		STATUS mandatory
		DESCRIPTION	 
		"Wireless Statistics. 22 elements(ULONG)."
		::= {WLstatisticsGRP 1 }


-------------------------------Site Survey----------------------

WLSiteSurveyGRP OBJECT IDENTIFIER ::= {wireless 4}

ChannelStatus OBJECT-TYPE
		SYNTAX OCTET STRING (SIZE (14))
		ACCESS read-only
		STATUS mandatory
		DESCRIPTION	 
		"."
		::= {WLSiteSurveyGRP 1}


-------------------------------Associated Station----------------------
-----------------------------------------------------------------------

AssociatedStationsGRP OBJECT IDENTIFIER ::= {wireless 5}

AssociatedSTAsNum OBJECT-TYPE
      SYNTAX  INTEGER (1..2007)
      ACCESS  read-only
      STATUS  mandatory
      DESCRIPTION
      "This parameter's value indicates the number of the currently
      associated STAtions. Associated STAtions should not be more
      than 2007."
      ::= { AssociatedStationsGRP 1 }

		
AssociatedSTAsInfo	OBJECT-TYPE
	    SYNTAX	OCTET STRING (SIZE (24))
	    ACCESS  read-only
	    STATUS  mandatory
	    DESCRIPTION
	    "The associated STAtion's Information."
	    ::= { AssociatedStationsGRP 2 }
		

-------------------------------Authorized Mac Addresses----------------------

AuthorizedMacAddressesGRP OBJECT IDENTIFIER ::= {wireless 6}

AuthorizationMacEnable OBJECT-TYPE
		SYNTAX INTEGER {enable(1),disable(2)}
		ACCESS read-write
		STATUS mandatory
		DESCRIPTION	 
		"."
		::= {AuthorizedMacAddressesGRP 1}



AuthorizedMac	OBJECT-TYPE
	    SYNTAX	OCTET STRING (SIZE (64))
	    ACCESS  read-write
	    STATUS  mandatory
	    DESCRIPTION
	    "The Authorized Wireless Mac Addresses."
	    ::= { AuthorizedMacAddressesGRP 2 }


-----------------------------KNOWN ACCESS POINTS----------------------


WLKnownAPGRP OBJECT IDENTIFIER ::= {wireless 7}

wirelessKnownAPsNum OBJECT-TYPE
		SYNTAX INTEGER (1..8)
		ACCESS read-only
		STATUS mandatory
		DESCRIPTION	 
		"."
		::= {WLKnownAPGRP 1 }



wirelessKnownAPs OBJECT-TYPE
		SYNTAX OCTET STRING (SIZE (32))
		ACCESS read-only
		STATUS mandatory
		DESCRIPTION	 
		"."
		::= {WLKnownAPGRP 2 }



--*************************** Traps ***************************
--*************************************************************

trapSTAMacAddress OBJECT-TYPE
	SYNTAX OCTET STRING (SIZE (6))
	ACCESS read-only
	STATUS mandatory
	DESCRIPTION	 
	"The MAC address of a station device"

	::= {traps 1}


trapReassociation TRAP-TYPE
	ENTERPRISE atmel
	VARIABLES {
	trapSTAMacAddress
	}
	DESCRIPTION
	"This trap message is sent when a STAtion's reassosiation
	request is received."
	::= 1

trapRoamOut TRAP-TYPE
	ENTERPRISE atmel
	VARIABLES {
	trapSTAMacAddress
	}
	DESCRIPTION
	"This trap message is used to indicate tha a STAtion has
	roamed out of the Wireless bridge's coverage area."
	::= 2

trapAssociation TRAP-TYPE
	ENTERPRISE atmel
	VARIABLES {
	trapSTAMacAddress
	}
	DESCRIPTION
	"Indicates the reception of an association request packet
	and	the sender STAtion's successful association with the
	Wireless Bridge."
	::= 3
	
trapDisassociation TRAP-TYPE
	ENTERPRISE atmel
	VARIABLES {
	trapSTAMacAddress
	}
	DESCRIPTION
	"This trap message is sent when a dissasociation notification
	packet is received from a STAtion."
	::= 4

trapAssociationExpire TRAP-TYPE
	ENTERPRISE atmel
	VARIABLES {
	trapSTAMacAddress
	}
	DESCRIPTION
	"When the association's maximum time interval expires for
	an associated STAtion this trap message is sent."
	::= 5

trapReset TRAP-TYPE
	ENTERPRISE atmel
	VARIABLES {
	sysReset
	}
	DESCRIPTION
	"This trap message is sent when Bridge Resets."
	::= 6

trapSettingPingIPAddress TRAP-TYPE
	ENTERPRISE atmel
	VARIABLES {
	operIPAddress
	}
	DESCRIPTION
	"This trap message is sent when the ATMEL Bridge IP address
	is set with the transmition of a ping message."
	::= 7

trapStartUp TRAP-TYPE
	ENTERPRISE atmel
	VARIABLES {
	}
	DESCRIPTION
	"This trap message is sent when Bridge Starts Up."
	::= 8

trapFailedToEraseFlash TRAP-TYPE
	ENTERPRISE atmel
	VARIABLES {
	}
	DESCRIPTION
	"This trap message is sent when Bridge Failed To Erase Flash."
	::= 9


END
